# -*- coding: utf-8 -*-
# shkiv_param.FCMacro
#
# Параметрический ведомый шкив GT2 с седлом под трубу руки и прижимной
# крышкой. Все размеры заданы ОДНИМ набором переменных (VarSet "Привод"),
# который виден в дереве документа — менять их можно прямо в GUI, модель
# пересчитается сама. Макрос нужен только чтобы построить/перестроить
# цепочку фич; после этого он не требуется.
#
# Что завязано на переменные:
#   * диаметр шкива        <- Ratio (передаточное число) и DriverTeeth
#   * положение шкива      <- Ratio и BeltLength (решение формулы ремня)
#   * седло/крышка/винты   <- TubeOD (наружный Ø трубы руки)
#
# Геометрия собрана на примитивах PartDesign (AdditiveCylinder/Box,
# SubtractiveCylinder/Box), а не на эскизах: у примитива каждый размер —
# отдельное свойство, которое можно привязать выражением, и нет привязки
# к именам рёбер (topological naming).
#
# Компоновка как в референсе-драйботе (makerworld 712239): корень руки
# прижимается к верху шкива крышкой на винтах. Там это плоская пластина
# и два винта на 28 мм; здесь — полукруглое седло под трубу и крышка.
#
# Запуск: FreeCAD -> Макросы... -> shkiv_param.FCMacro

import math
import re

import FreeCAD as App

DOC_HINT   = "ETZ_Robot"
PART_NAME  = "Part002"     # контейнер, который двигается на межосевое расстояние
BODY_NAME  = "Body003"     # тело шкива (существующее, переиспользуется)
CAP_NAME   = "Body_Cap"    # тело крышки (создаётся)
PROST_NAME = "Body_Prost"  # тело проставки под второй шкив (создаётся)
VS_NAME    = "Drive"
POSE_NAME  = "Poza"       # поза руки: углы плеча, локтя и рычага (отдельно от Drive)

PULLEY_LABEL = "Шкив_ведомый"
CAP_LABEL    = "Крышка_хомута"
PROST_LABEL  = "Проставка_шкивов"
PUL2_NAME    = "Body_Pulley2"   # второй ведомый шкив (создаётся)
PUL2_LABEL   = "Шкив_ведомый_2"
TUBE_PART    = "Part_Tube"      # отдельный парт с трубой руки (создаётся)
TUBE_BODY    = "Body_Tube"
TUBE_PLABEL  = "Труба_руки"
TUBE_BLABEL  = "Труба_Ø10"
ELBOW_NAME   = "Body_Elbow"     # хомут локтя на трубе 1 (создаётся)
ELBOW_LABEL  = "Локоть_хомут_1"
ELBCAP_NAME  = "Body_ElbowCap"
ELBCAP_LABEL = "Локоть_крышка_1"
ELBOW2_NAME  = "Body_Elbow2"    # хомут локтя на трубе 2, вращается
ELBOW2_LABEL = "Локоть_хомут_2"
ELB2CAP_NAME = "Body_Elbow2Cap"
ELB2CAP_LABEL= "Локоть_крышка_2"
TUBE2_NAME   = "Body_Tube2"     # вторая труба, проходит локоть насквозь
TUBE2_LABEL  = "Труба_2_Ø10"
ROD_NAME     = "Body_Rod"       # тяга параллелограмма (создаётся)
ROD_LABEL    = "Тяга"
JOINT_NAME   = "Body_RodJoint"  # шарнир тяги на конце трубы 2
JOINT_LABEL  = "Шарнир_тяги"
JNTCAP_NAME  = "Body_RodJointCap"
JNTCAP_LABEL = "Шарнир_тяги_крышка"
DRV2_NAME    = "Driver2"        # ссылка на ведущий шкив правого мотора
DRV2_LABEL   = "Шкив_ведущий_2"
MOTOR2_NAME  = "Body001"        # правый мотор (существующий)
DRIVER_NAME  = "Pulley"         # ведущий шкив левого мотора (существующий)

# ---------------------------------------------------------------------------
# Переменные. (значение по умолчанию, тип, группа, подсказка)
# ВАЖНО: имя свойства не должно совпадать с обозначением единицы измерения —
# "C", "T", "N", "F", "W" и т.п. парсер выражений читает как кулон/теслу/
# ньютон, и выражение молча перестаёт вычисляться.
# ---------------------------------------------------------------------------
INPUTS = [
    ("DriverTeeth",        "App::PropertyInteger", "1 Передача", 20,
     "Зубьев на ведущем шкиве (на валу мотора)"),
    ("Ratio",     "App::PropertyFloat",   "1 Передача", 4.0,
     "Передаточное число. Зубья ведомого = round(DriverTeeth * Ratio)"),
    ("BeltLength",   "App::PropertyLength",  "1 Передача", 320.0,
     "Длина ремня по каталогу, мм (GT2-320 = 160 зубьев). Задаёт, насколько "
     "ЛЕВЫЙ мотор позади оси руки. Моторы перевёрнуты, их корпуса на высоте "
     "тяги, и при плече около -110° планка тяги проходит мимо угла левого "
     "мотора: с 300 зазор был 1 мм, с 320 — с запасом. Правому мотору "
     "хватает 300, он встаёт на 10 мм впереди левого (Motor2X)"),
    ("BeltPitch",    "App::PropertyLength",  "1 Передача", 2.0,
     "Шаг ремня: GT2 = 2 мм"),
    ("BeltWidth", "App::PropertyLength",  "1 Передача", 6.0,
     "Ширина ремня, мм"),
    ("BeltPlaneZ",        "App::PropertyLength",  "1 Передача", 17.5,
     "Z нижней кромки венца первой ступени (глобально, низ левого мотора "
     "был z 0). Задаёт высоту ВСЕЙ руки: шкивы, плечо, локоть. 17.5 — "
     "ниже нельзя: винт шарнира локтя опускается до поле+30, а над полем "
     "стоят стопки по 25 мм. Моторы висят над венцом валом вниз"),
    ("DrvGap",            "App::PropertyLength",  "1 Передача", 2.5,
     "Зазор от фланца мотора до ступицы ведущего шкива 20T. Венец шкива "
     "лежит на DrvGap + 8..15 мм ниже фланца (ступица 7, буртик 1, зубья 7). "
     "Меньше 2.5 нельзя — ступица упрётся в буртик мотора. Задаёт и высоту "
     "плиты мотора 1, над которой ходит тяга. 2.5 — чтобы плита 1 (фанера "
     "6) легла ровно на латунные стойки M3x30"),
    ("MotorLen",          "App::PropertyLength",  "7 Моторы", 40.0,
     "Длина корпуса NEMA17 (модель Body: корпус 40, буртик 2, вал 24)"),
    ("Plate2T",           "App::PropertyLength",  "7 Моторы", 6.0,
     "Плита правого мотора — фанера. Мотор стоит валом ВВЕРХ и висит под "
     "ней на 4 винтах, ведущий шкив над плитой"),
    ("Drv2Gap",           "App::PropertyLength",  "7 Моторы", 2.0,
     "Зазор от плиты правого мотора до нижнего фланца ведущего шкива 2"),

    ("DriverTeeth2",       "App::PropertyInteger", "1 Передача 2", 20,
     "Зубьев на ведущем шкиве ВТОРОЙ ступени (на своём мотоpе)"),
    ("BeltLength2",   "App::PropertyLength",  "1 Передача 2", 300.0,
     "Длина ремня второй ступени. Из неё считается своё межосевое и "
     "положение правого мотора по Y"),
    ("Ratio2",    "App::PropertyFloat",   "1 Передача 2", 4.0,
     "Передача второй ступени. Независима от Ratio — верхний шкив "
     "считается только по ней"),

    ("FlangeThk",   "App::PropertyLength",  "2 Шкив", 1.5,  "Толщина фланца"),
    ("FlangeLip",    "App::PropertyLength",  "2 Шкив", 2.0,
     "На сколько фланец больше вершин зубьев (на сторону)"),
    ("BrgOD",       "App::PropertyLength",  "2 Шкив", 22.0, "Наружный Ø подшипника (608ZZ = 22)"),
    ("BrgW",        "App::PropertyLength",  "2 Шкив", 7.0,  "Толщина подшипника (608ZZ = 7)"),
    ("ShaftHoleD",      "App::PropertyLength",  "2 Шкив", 14.0,
     "Ø отверстия в упоре над подшипником. Больше внутреннего кольца "
     "608ZZ (Ø12): сквозь него проставка достаёт до внутреннего кольца, "
     "а упор шкива ложится только на наружное — трущихся пар нет"),
    ("WindowCount",    "App::PropertyInteger", "2 Шкив", 3,
     "Число окон облегчения. В референсе 3; спица всегда приходится под руку"),
    ("WindowAngle",      "App::PropertyAngle",   "2 Шкив", 55.0,
     "Угловая ширина одного окна. Остаток до 360/WindowCount — ширина спицы"),
    ("WindowGapIn","App::PropertyLength",  "2 Шкив", 3.0,
     "Отступ окна наружу от гнезда подшипника"),
    ("WindowGapOut",  "App::PropertyLength",  "2 Шкив", 4.0,
     "Отступ окна внутрь от вершин зубьев (толщина обода под ремень)"),

    ("FlangeThk2",  "App::PropertyLength",  "2 Шкив 2", 1.5,
     "Толщина фланца верхнего шкива"),
    ("FlangeLip2",   "App::PropertyLength",  "2 Шкив 2", 2.0,
     "На сколько фланец верхнего шкива больше вершин зубьев (на сторону)"),
    ("BeltWidth2","App::PropertyLength",  "2 Шкив 2", 6.0,
     "Ширина ремня второй ступени"),
    ("BrgOD2",      "App::PropertyLength",  "2 Шкив 2", 22.0,
     "Наружный Ø подшипника верхнего шкива (608ZZ = 22)"),
    ("BrgW2",       "App::PropertyLength",  "2 Шкив 2", 7.0,
     "Толщина подшипника верхнего шкива (608ZZ = 7)"),
    ("ShaftHoleD2",     "App::PropertyLength",  "2 Шкив 2", 14.0,
     "Ø отверстия в упоре верхнего шкива. Как у первого: сквозь него "
     "верхняя втулка вала прижимает внутреннее кольцо"),
    ("WindowCount2",   "App::PropertyInteger", "2 Шкив 2", 3,
     "Число окон облегчения верхнего шкива"),
    ("WindowAngle2",     "App::PropertyAngle",   "2 Шкив 2", 55.0,
     "Угловая ширина одного окна верхнего шкива"),
    ("WindowGapIn2","App::PropertyLength", "2 Шкив 2", 3.0,
     "Отступ окна верхнего шкива наружу от гнезда подшипника"),
    ("WindowGapOut2", "App::PropertyLength",  "2 Шкив 2", 4.0,
     "Отступ окна верхнего шкива внутрь от вершин зубьев"),

    ("TubeOD",     "App::PropertyLength",  "3 Рука", 10.0,
     "НАРУЖНЫЙ Ø трубы руки. Меняется свободно — седло, крышка и винты пересчитаются"),
    ("ClampLen",  "App::PropertyLength",  "3 Рука", 30.0, "Длина хомута вдоль трубы"),
    ("ClampStartR",    "App::PropertyLength",  "3 Рука", 13.0,
     "С какого радиуса начинается седло (должен быть больше радиуса гнезда подшипника)"),
    ("SaddleWall",   "App::PropertyLength",  "3 Рука", 4.0,  "Материал под дном жёлоба"),
    ("CapWall", "App::PropertyLength",  "3 Рука", 3.0,  "Материал над трубой в крышке"),
    ("ScrewM",         "App::PropertyLength",  "3 Рука", 3.0,  "Номинал винта хомута: 3 = M3"),
    ("NutAF",       "App::PropertyLength",  "3 Рука", 5.8,
     "Размер под ключ паза гайки. M3 = 5.5 + 0.3 на усадку печати"),
    ("NutThk",    "App::PropertyLength",  "3 Рука", 2.8,
     "Высота паза гайки. M3 = 2.4 + 0.4 на усадку печати"),

    ("SpacerID",    "App::PropertyLength",  "4 Проставка", 8.2,
     "Внутренний Ø проставки: сидит на валу M8 с зазором 0.2"),
    ("SpacerWall",   "App::PropertyLength",  "4 Проставка", 1.9,
     "Толщина стенки проставки. Наружный Ø = 12 — по внутреннему кольцу "
     "608ZZ: проставка зажата между внутренними кольцами и не вращается"),
    ("SpacerGap",    "App::PropertyLength",  "4 Проставка", 2.0,
     "Зазор между верхом крышки хомута и низом второго шкива"),

    ("LeverLen",   "App::PropertyLength",  "4 Рычаг", 50.0,
     "Длина рычага: от оси шкива до центра отверстия на конце"),
    ("LeverWidth", "App::PropertyLength",  "4 Рычаг", 12.0, "Ширина рычага"),
    ("LeverThk",   "App::PropertyLength",  "4 Рычаг", 4.0,
     "Толщина рычага. Он висит ПОД нижним фланцем, в полосу ремня не лезет"),
    ("LeverHoleD",     "App::PropertyLength",  "4 Рычаг", 3.2,
     "Ø отверстия на конце рычага (3.2 = свободный M3)"),

    ("TubeLen",       "App::PropertyLength",  "3 Рука", 150.0,
     "Длина трубы руки от начала хомута наружу"),
    ("TubeWall",      "App::PropertyLength",  "3 Рука", 1.0,
     "Толщина стенки трубы руки"),

    ("Tube2Len",      "App::PropertyLength",  "3 Рука 2", 120.0,
     "Рабочая длина второй трубы: от грани локтя наружу"),
    ("ElbowGrip",     "App::PropertyLength",  "3 Рука 2", 25.0,
     "На сколько конец первой трубы входит в локоть"),
    ("ElbowWall",     "App::PropertyLength",  "3 Рука 2", 3.0,
     "Толщина стенки локтя вокруг трубы"),

    ("PivotBrgOD",    "App::PropertyLength",  "3 Локоть", 10.0,
     "Наружный Ø подшипника шарнира (623ZZ = 10)"),
    ("PivotBrgW",     "App::PropertyLength",  "3 Локоть", 4.0,
     "Толщина подшипника шарнира (623ZZ = 4)"),
    ("PivotHeadC",    "App::PropertyLength",  "3 Локоть", 3.5,
     "Высота кармана под головку винта шарнира (головка M3 ISO4762 = 3)"),
    ("PivotBoss",     "App::PropertyLength",  "3 Локоть", 0.5,
     "Высота буртика Ø5.5 на проушине хомута 1 под ВНУТРЕННИМ кольцом "
     "623ZZ. Без него наружное кольцо (крутится с хомутом 2) лежит на "
     "хомуте 1 и трётся о него"),
    ("ClampNutLift",  "App::PropertyLength",  "3 Локоть", 1.2,
     "На сколько гнёзда гаек хомутов локтя (и шарнира) подняты над нижней "
     "гранью. Пол 1.2 мм держит гайку, а винт берётся M3x12 вместо M3x16 — "
     "кончик не торчит под хомутом: там ходит тяга, а под рукой стопки "
     "шашек"),
    ("PivotGap",      "App::PropertyLength",  "3 Локоть", 1.0,
     "Зазор между торцом первой трубы и проушиной шарнира"),
    ("ElbowLift",     "App::PropertyLength",  "3 Локоть", 3.0,
     "На сколько поднять предплечье над минимумом. Без подъёма угол "
     "хомута 2 (R17) при диагональных углах в локте на 2 мм заходит по "
     "высоте в крышку хомута 1"),

    ("RodThk",        "App::PropertyLength",  "4 Тяга", 4.0,
     "Толщина тяги = ширина подшипника 623ZZ (PivotBrgW): он запрессован "
     "в глаз заподлицо с обеих сторон"),
    ("RodWall",       "App::PropertyLength",  "4 Тяга", 2.5,
     "Материал глаза тяги вокруг гнезда подшипника"),
    ("RodBarW",       "App::PropertyLength",  "4 Тяга", 8.0,
     "Ширина планки тяги между глазами"),
    ("RodStandoff",   "App::PropertyLength",  "4 Тяга", 3.0,
     "Высота втулки между рычагом (проушиной) и внутренним кольцом "
     "подшипника тяги. Опускает тягу ниже хомута шарнира тяги (иначе при "
     "углах в локте не 90 градусов тяга въезжает в него), но не ниже, чем "
     "надо: под тягой плита мотора 1. Сейчас 2 мм до хомута и 2.5 до плиты"),

    ("JointGrip",     "App::PropertyLength",  "4 Тяга", 20.0,
     "На сколько хомут шарнира тяги садится на конец трубы 2"),
    ("JointWall",     "App::PropertyLength",  "4 Тяга", 3.0,
     "Стенка проушины тяги вокруг отверстия, она же торцевая стенка хомута"),

    ("MotorSize",     "App::PropertyLength",  "7 Моторы", 42.3,
     "Габарит корпуса мотора (NEMA17 = 42.3). Из него считается шаг"),
    ("MotorGap",      "App::PropertyLength",  "7 Моторы", 3.0,
     "Зазор между корпусами моторов. Шаг = MotorSize + MotorGap"),

    ("ToothR",        "App::PropertyLength",  "4 Профиль GT2", 0.555,
     "Радиус канавки зуба GT2"),
    ("ToothOffset",     "App::PropertyLength",  "4 Профиль GT2", 0.449,
     "Центр канавки на радиусе PD/2 - ToothOffset"),
]

# производные: (имя, тип, группа, выражение, подсказка)
DERIVED = [
    ("DrivenTeeth",   "App::PropertyInteger", "5 Расчёт", "round({V}.DriverTeeth * {V}.Ratio)",
     "Зубьев на ведомом шкиве (целое)"),
    ("RatioActual", "App::PropertyFloat", "5 Расчёт", "{V}.DrivenTeeth / {V}.DriverTeeth",
     "Фактическая передача после округления зубьев"),
    ("PitchD1",    "App::PropertyLength",  "5 Расчёт", "{V}.DriverTeeth * {V}.BeltPitch / pi",
     "Делительный Ø ведущего"),
    ("PitchD2",    "App::PropertyLength",  "5 Расчёт", "{V}.DrivenTeeth * {V}.BeltPitch / pi",
     "Делительный Ø ведомого"),
    ("TipD",  "App::PropertyLength",  "5 Расчёт", "{V}.PitchD2 - 0.508 mm",
     "Ø по вершинам зубьев ведомого"),
    ("FlangeD",    "App::PropertyLength",  "5 Расчёт", "{V}.TipD + 2 * {V}.FlangeLip",
     "Наружный Ø фланцев"),
    # межосевое: C = (b + sqrt(b^2 - 8Q)) / 4,  b = L - pi(D1+D2)/2,  Q = (D2-D1)^2/4
    ("BeltB",     "App::PropertyLength",  "5 Расчёт",
     "{V}.BeltLength - pi * ({V}.PitchD1 + {V}.PitchD2) / 2", "Промежуточная величина b"),
    ("BeltQ",     "App::PropertyArea",    "5 Расчёт",
     "({V}.PitchD2 - {V}.PitchD1) ^ 2 / 4", "Промежуточная величина Q"),
    # max(...; 0) обязателен: при слишком коротком ремне подкоренное уходит
    # в минус, sqrt даёт nan, и узел уезжает в неопределённую точку.
    ("CenterDist",     "App::PropertyLength",  "5 Расчёт",
     "({V}.BeltB + sqrt(max({V}.BeltB ^ 2 - 8 * {V}.BeltQ; 0 mm^2) / 1mm^2) * 1mm) / 4",
     "МЕЖОСЕВОЕ расстояние от вала мотора — на него сдвинут весь узел"),
    ("BeltMin",   "App::PropertyLength",  "5 Расчёт",
     "({V}.PitchD1 + {V}.PitchD2) + pi * ({V}.PitchD1 + {V}.PitchD2) / 2"
     " + ({V}.PitchD2 - {V}.PitchD1) ^ 2 / (2 * ({V}.PitchD1 + {V}.PitchD2))",
     "Абсолютный минимум длины ремня для этих шкивов (шкивы вплотную)"),
    ("BeltSlack","App::PropertyLength",  "5 Расчёт",
     "{V}.BeltLength - {V}.BeltMin",
     "Запас длины ремня. <= 0 означает, что ремень физически не налезет"),
    ("TeethInMesh", "App::PropertyFloat", "5 Расчёт",
     "(180 - 2 * asin(({V}.PitchD2 - {V}.PitchD1) / (2 * {V}.CenterDist)) / 1deg) / 360"
     " * {V}.DriverTeeth",
     "Зубьев ведущего шкива в зацеплении. Меньше 6 — ремень будет проскакивать"),

    # --- вторая ступень: свои зубья и диаметры, межосевое общее ---
    # Шкивы соосны, поэтому межосевое у второй ступени то же самое, а вот
    # длина ремня из него уже выводится, а не задаётся.
    ("DrivenTeeth2",  "App::PropertyInteger", "5 Расчёт 2",
     "round({V}.DriverTeeth2 * {V}.Ratio2)", "Зубьев на верхнем ведомом шкиве"),
    ("RatioActual2", "App::PropertyFloat", "5 Расчёт 2",
     "{V}.DrivenTeeth2 / {V}.DriverTeeth2", "Фактическая передача второй ступени"),
    ("PitchDriver2", "App::PropertyLength", "5 Расчёт 2",
     "{V}.DriverTeeth2 * {V}.BeltPitch / pi", "Делительный Ø ведущего 2"),
    ("PitchDriven2",  "App::PropertyLength", "5 Расчёт 2",
     "{V}.DrivenTeeth2 * {V}.BeltPitch / pi", "Делительный Ø верхнего ведомого"),
    ("TipD2", "App::PropertyLength",  "5 Расчёт 2",
     "{V}.PitchDriven2 - 0.508 mm", "Ø по вершинам зубьев верхнего шкива"),
    ("FlangeD2",   "App::PropertyLength",  "5 Расчёт 2",
     "{V}.TipD2 + 2 * {V}.FlangeLip2", "Наружный Ø фланцев верхнего шкива"),
    # межосевое второй ступени — та же формула длины ремня, что у первой
    ("BeltB2",     "App::PropertyLength", "5 Расчёт 2",
     "{V}.BeltLength2 - pi * ({V}.PitchDriver2 + {V}.PitchDriven2) / 2",
     "Промежуточная величина b второй ступени"),
    ("BeltQ2",     "App::PropertyArea",   "5 Расчёт 2",
     "({V}.PitchDriven2 - {V}.PitchDriver2) ^ 2 / 4",
     "Промежуточная величина Q второй ступени"),
    ("CenterDist2","App::PropertyLength", "5 Расчёт 2",
     "({V}.BeltB2 + sqrt(max({V}.BeltB2 ^ 2 - 8 * {V}.BeltQ2; 0 mm^2) / 1mm^2)"
     " * 1mm) / 4",
     "МЕЖОСЕВОЕ второй ступени: от вала правого мотора до общей оси шкивов"),
    ("BeltMin2",   "App::PropertyLength", "5 Расчёт 2",
     "({V}.PitchDriver2 + {V}.PitchDriven2)"
     " + pi * ({V}.PitchDriver2 + {V}.PitchDriven2) / 2"
     " + ({V}.PitchDriven2 - {V}.PitchDriver2) ^ 2"
     " / (2 * ({V}.PitchDriver2 + {V}.PitchDriven2))",
     "Минимум длины ремня второй ступени (шкивы вплотную)"),
    ("BeltSlack2", "App::PropertyLength", "5 Расчёт 2",
     "{V}.BeltLength2 - {V}.BeltMin2", "Запас длины ремня второй ступени"),
    ("TeethInMesh2", "App::PropertyFloat", "5 Расчёт 2",
     "(180 - 2 * asin(({V}.PitchDriven2 - {V}.PitchDriver2) / (2 * {V}.CenterDist2))"
     " / 1deg) / 360 * {V}.DriverTeeth2",
     "Зубьев ведущего 2 в зацеплении. Меньше 6 — ремень будет проскакивать"),

    # --- габариты верхнего шкива, все от своих переменных ---
    ("RimH2",  "App::PropertyLength", "6 Производные 2",
     "{V}.BeltWidth2 + 1 mm", "Высота венца верхнего шкива"),
    ("PulleyH2", "App::PropertyLength", "6 Производные 2",
     "2 * {V}.FlangeThk2 + {V}.RimH2", "Полная высота верхнего шкива"),
    ("WindowRin2",      "App::PropertyLength", "6 Производные 2",
     "{V}.BrgOD2 / 2 + {V}.WindowGapIn2",
     "Внутренний радиус окон верхнего шкива"),
    ("WindowRout2",     "App::PropertyLength", "6 Производные 2",
     "{V}.TipD2 / 2 - {V}.WindowGapOut2",
     "Наружный радиус окон верхнего шкива"),
    ("WindowPhase2",     "App::PropertyAngle",  "6 Производные 2",
     "180 deg / {V}.WindowCount2 - {V}.WindowAngle2 / 2",
     "Доворот первого окна верхнего шкива, чтобы спица пришлась под рычаг"),
    ("ShoulderThk2",    "App::PropertyLength", "6 Производные 2",
     "{V}.PulleyH2 - {V}.BrgW2",
     "Толщина упора над подшипником верхнего шкива. <= 0 — подшипник "
     "не во что упереть"),

    ("RimH",  "App::PropertyLength", "6 Производные", "{V}.BeltWidth + 1 mm",
     "Высота венца под ремень"),
    ("PulleyH", "App::PropertyLength", "6 Производные",
     "2 * {V}.FlangeThk + {V}.RimH", "Полная высота шкива"),
    ("SaddleH",  "App::PropertyLength", "6 Производные",
     "{V}.TubeOD / 2 + {V}.SaddleWall", "Высота седла над верхом шкива"),
    ("TubeAxisZ",      "App::PropertyLength", "6 Производные",
     "{V}.PulleyH + {V}.SaddleH", "Высота оси трубы (= верх седла)"),
    ("SaddleHalfW","App::PropertyLength", "6 Производные",
     "{V}.TubeOD / 2 + {V}.ScrewM + 3.5 mm", "Полуширина седла/крышки"),
    ("ScrewY",        "App::PropertyLength", "6 Производные",
     "{V}.TubeOD / 2 + {V}.ScrewM / 2 + 1.3 mm", "Смещение винтов от оси трубы"),
    ("ScrewX1",       "App::PropertyLength", "6 Производные",
     "{V}.ClampStartR + 6 mm", "Первая пара винтов"),
    ("ScrewX2",       "App::PropertyLength", "6 Производные",
     "{V}.ClampStartR + {V}.ClampLen - 6 mm", "Вторая пара винтов"),
    ("CapThk", "App::PropertyLength", "6 Производные",
     "{V}.TubeOD / 2 + {V}.CapWall", "Толщина крышки"),
    ("WindowRin",      "App::PropertyLength", "6 Производные",
     "{V}.BrgOD / 2 + {V}.WindowGapIn", "Внутренний радиус окон"),
    ("WindowRout",     "App::PropertyLength", "6 Производные",
     "{V}.TipD / 2 - {V}.WindowGapOut", "Наружный радиус окон"),
    ("WindowPhase",     "App::PropertyAngle",  "6 Производные",
     "180 deg / {V}.WindowCount - {V}.WindowAngle / 2",
     "Доворот первого окна, чтобы спица пришлась ровно под седло руки"),
    ("SpacerOD",    "App::PropertyLength", "6 Производные",
     "{V}.SpacerID + 2 * {V}.SpacerWall", "Наружный Ø проставки"),
    # вся высота второго шкива считается от требования «рычаг не задевает
    # крышку хомута»: низ рычага = верх крышки + SpacerGap
    ("Pulley2Z",      "App::PropertyLength", "6 Производные",
     "{V}.TubeAxisZ + {V}.CapThk + {V}.SpacerGap + {V}.LeverThk"
     " - {V}.FlangeThk2",
     "Низ нижнего фланца второго шкива. Рычаг — утолщение этого фланца "
     "вниз, поэтому фланец поднят на LeverThk - FlangeThk"),
    ("LeverZ",     "App::PropertyLength", "6 Производные",
     "{V}.Pulley2Z + {V}.FlangeThk2 - {V}.LeverThk",
     "Низ рычага — самая низкая точка второго шкива"),
    ("SpacerH",  "App::PropertyLength", "6 Производные",
     "{V}.Pulley2Z - {V}.BrgW",
     "Высота проставки: от верха подшипника 1 до низа подшипника 2 (BrgZ2 "
     "= Pulley2Z). Зажата между внутренними кольцами — трущихся пар нет"),
    ("LeverR0",     "App::PropertyLength", "6 Производные",
     "{V}.BrgOD2 / 2 + 2 mm",
     "С какого радиуса начинается рычаг: до центра он не доходит, иначе "
     "перекрыл бы гнездо подшипника снизу"),
    ("BeltPlaneZ2",      "App::PropertyLength", "6 Производные",
     "{V}.Pulley2Z + {V}.FlangeThk",
     "Венец второго шкива от низа первого — на эту высоту ставить второй "
     "ведущий шкив"),
    ("BrgZ2",      "App::PropertyLength", "6 Производные",
     "{V}.Pulley2Z",
     "Низ гнезда подшипника второго шкива. Гнездо открыто ВНИЗ, как у "
     "первого шкива, а сверху остаётся упор с отверстием ShaftHoleD"),
    ("Tube1End",     "App::PropertyLength", "6 Производные 2",
     "{V}.ClampStartR + {V}.TubeLen", "Где кончается первая труба"),
    ("ElbowHalfW",   "App::PropertyLength", "6 Производные 2",
     "{V}.SaddleHalfW",
     "Полуширина хомутов локтя — та же, что у седла на шкиве, чтобы "
     "винты M3 встали по той же схеме"),
    ("PivotLugR",    "App::PropertyLength", "6 Производные 2",
     "{V}.PivotBrgOD / 2 + {V}.ElbowWall", "Радиус проушины шарнира"),

    ("PivotCeil",    "App::PropertyLength", "6 Производные 2",
     "{V}.PivotHeadC + 1.5 mm",
     "Потолок над гнездом подшипника: карман под головку винта плюс стенка"),
    ("Tube2Z",       "App::PropertyLength", "6 Производные 2",
     "{V}.TubeAxisZ + {V}.PivotBrgW + {V}.PivotCeil + {V}.TubeOD / 2"
     " + {V}.ElbowLift",
     "Ось второй трубы по высоте: она идёт НАД шарниром, поэтому оси "
     "труб не пересекаются"),
    ("ElbowEndX",    "App::PropertyLength", "6 Производные 2",
     "max({V}.PivotGap + {V}.PivotLugR; {V}.ElbowHalfW + 1 mm)",
     "Насколько торец первой трубы отстоит от оси шарнира. Не меньше "
     "полуширины хомута 2 плюс зазор, иначе хомут 2 при повороте наедет "
     "на крышку хомута 1"),
    ("PivotX",       "App::PropertyLength", "6 Производные 2",
     "{V}.Tube1End + {V}.ElbowEndX",
     "ОСЬ ШАРНИРА. Отсюда считаются длины звеньев: плечо = PivotX от оси "
     "шкива, вылет предплечья = LeverLen от этой оси. Считается через "
     "ElbowEndX, иначе жёлоб хомута кончится не там, где труба"),
    ("ElbowScrewY",  "App::PropertyLength", "6 Производные 2",
     "{V}.ScrewY",
     "Смещение винтов хомутов локтя от оси трубы — та же формула, что у "
     "винтов хомута на шкиве"),
    ("ElbowScrewX1", "App::PropertyLength", "6 Производные 2",
     "{V}.ElbowEndX + 6 mm", "Первая пара винтов хомута 1 (от оси шарнира)"),
    ("ElbowScrewX2", "App::PropertyLength", "6 Производные 2",
     "{V}.ElbowEndX + {V}.ElbowGrip - 6 mm", "Вторая пара винтов хомута 1"),
    ("Elbow2ScrewX", "App::PropertyLength", "6 Производные 2",
     "{V}.ElbowGrip / 2 - 6 mm", "Винты хомута 2, симметрично оси шарнира"),
    ("ElbowBot",     "App::PropertyLength", "6 Производные 2",
     "{V}.TubeOD / 2 + {V}.ElbowWall", "Глубина хомута под осью трубы"),
    ("Elbow2Bot",    "App::PropertyLength", "6 Производные 2",
     "{V}.PivotBrgW + {V}.PivotCeil + {V}.TubeOD / 2 + {V}.ElbowLift"
     " - {V}.PivotBoss",
     "От оси трубы 2 до низа проушины хомута 2"),
    ("RodEyeR",      "App::PropertyLength", "6 Производные 2",
     "{V}.PivotBrgOD / 2 + {V}.RodWall",
     "Радиус глаза тяги вокруг гнезда подшипника 623ZZ"),
    ("RodZ",         "App::PropertyLength", "6 Производные 2",
     "{V}.LeverZ - {V}.RodStandoff - {V}.RodThk",
     "Низ тяги. Тяга висит под рычагом и проушиной на втулках RodStandoff "
     "— ниже хомутов предплечья, поэтому не задевает их ни при каком угле"),
    ("JointEyeR",    "App::PropertyLength", "6 Производные 2",
     "max({V}.LeverHoleD / 2 + {V}.JointWall; {V}.LeverWidth / 2)",
     "Радиус проушины тяги. Не меньше глаза рычага, чтобы оба конца тяги "
     "были одинаковые"),
    ("JointReach",   "App::PropertyLength", "6 Производные 2",
     "{V}.JointEyeR + {V}.JointWall",
     "От торца трубы 2 до оси пальца тяги: на столько труба НЕ доходит до "
     "пальца, пролёт закрывает планка проушины"),
    ("JointPlateZ",  "App::PropertyLength", "6 Производные 2",
     "{V}.LeverZ - {V}.Tube2Z",
     "Низ планки проушины в локальных координатах хомута (от оси трубы 2). "
     "Полоса та же, что у рычага, поэтому тяга — плоская планка"),
    ("Tube2X0",      "App::PropertyLength", "6 Производные 2",
     "-{V}.LeverLen + {V}.JointReach",
     "Начало второй трубы ОТ ОСИ ШАРНИРА. Палец тяги стоит ровно на "
     "LeverLen — это и есть условие параллелограмма, — а труба кончается "
     "на JointReach раньше: до пальца её продолжает планка проушины"),
    ("Tube2Full",    "App::PropertyLength", "6 Производные 2",
     "{V}.LeverLen - {V}.JointReach + {V}.Tube2Len",
     "Полная длина второй трубы (дальний конец по-прежнему на Tube2Len "
     "от оси шарнира)"),
    ("JointMidX",    "App::PropertyLength", "6 Производные 2",
     "{V}.Tube2X0 + {V}.JointGrip / 2", "Середина хомута шарнира тяги"),
    ("JointScrewX",  "App::PropertyLength", "6 Производные 2",
     "{V}.JointGrip / 2 - 6 mm",
     "Винты хомута тяги, симметрично его середине"),
    # --- компоновка: моторы бок о бок ПОЗАДИ шкивов, рука выходит между
    # ними. Левый мотор — начало координат документа, поэтому двигается не
    # он, а узел руки: его ось уезжает на PulleyAxisX вперёд и на
    # ArmAxisY в сторону, ровно на середину между валами моторов.
    ("MotorPitch",   "App::PropertyLength", "7 Моторы",
     "{V}.MotorSize + {V}.MotorGap",
     "Шаг между валами моторов поперёк руки. Корпуса стоят с зазором "
     "MotorGap, плотнее некуда"),
    ("ArmAxisY",     "App::PropertyLength", "7 Моторы",
     "{V}.MotorPitch / 2",
     "Y оси шкивов = ровно середина между валами моторов, поэтому рука "
     "выходит между ними и оба ремня симметричны"),
    ("PulleyAxisX",  "App::PropertyLength", "7 Моторы",
     "sqrt(max({V}.CenterDist ^ 2 - {V}.ArmAxisY ^ 2; 0 mm^2) / 1mm^2) * 1mm",
     "X оси шкивов от левого мотора: остаток межосевого после сдвига на "
     "ArmAxisY. Рука смотрит вдоль +X, то есть ОТ моторов"),
    ("Motor2X",      "App::PropertyLength", "7 Моторы",
     "{V}.PulleyAxisX - sqrt(max({V}.CenterDist2 ^ 2 - {V}.ArmAxisY ^ 2;"
     " 0 mm^2) / 1mm^2) * 1mm",
     "X правого мотора: назад от оси шкивов на своё межосевое. При равных "
     "ремнях совпадает с левым (оба вала на одной линии)"),
    ("Motor2Y",      "App::PropertyLength", "7 Моторы",
     "{V}.MotorPitch",
     "Y правого мотора: шаг от левого. Ось руки проходит посередине"),
    ("Motor2Lift",   "App::PropertyLength", "6 Производные",
     "{V}.BeltPlaneZ2 - {V}.FlangeThk",
     "На сколько правый мотор выше левого, чтобы его венец совпал с венцом "
     "второго ведомого шкива"),
    ("Motor1FaceZ",  "App::PropertyLength", "7 Моторы",
     "{V}.BeltPlaneZ + {V}.DrvGap + 15 mm",
     "Фланец левого мотора. Он ПЕРЕВЁРНУТ: стоит фланцем вниз на плите, "
     "вал вниз, ведущий шкив под плитой на уровне венца ведомого"),
    ("Motor2FaceZ",  "App::PropertyLength", "7 Моторы",
     "{V}.BeltPlaneZ - 1 mm + {V}.Motor2Lift - {V}.Drv2Gap - {V}.Plate2T",
     "Фланец правого мотора. Он стоит валом ВВЕРХ под фанерной плитой: "
     "шкив 20T (низ — на 1 мм ниже венца) над плитой с зазором Drv2Gap"),
    ("NutCircumR",       "App::PropertyLength", "6 Производные",
     "{V}.NutAF / sqrt(3)", "Радиус описанной окружности шестигранника"),
    ("NutZ",       "App::PropertyLength", "6 Производные",
     "{V}.PulleyH",
     "Низ паза гайки. Равен низу седла: паз открыт вниз, подошвы под гайкой "
     "нет (её не на чем печатать там, где седло свисает за фланец)"),
]


# ---------------------------------------------------------------------------
# ПОЗА — отдельный VarSet «Poza». Углы не живут в Drive нарочно: FreeCAD
# пересчитывает КАЖДЫЙ объект, ссылающийся на изменённый VarSet, а на
# Drive ссылаются все тела, включая шкивы со 100-120 зубьями — поворот
# руки стоил 10 с пересчёта. На Poza ссылаются только Placement'ы и тяга,
# поэтому поворот почти бесплатный (и руку можно таскать мышью, см.
# ruka_mysh.FCMacro). Углы плеча и рычага — абсолютные (от +X), угол
# предплечья — относительно плеча.
POSE_INPUTS = [
    ("ShoulderAngle", "App::PropertyAngle", "Поза", 0.0,
     "Угол плеча (шкив 1 + рука) от +X. Поворачивает шкив 1, хомут, трубу "
     "и всё, что на ней"),
    ("Tube2Angle",    "App::PropertyAngle", "Поза", 90.0,
     "Угол предплечья в шарнире ОТНОСИТЕЛЬНО плеча. Поворачивает хомут 2, "
     "крышку и саму трубу"),
    ("LeverAngle",    "App::PropertyAngle", "Поза", -90.0,
     "Куда смотрит рычаг (шкив 2), абсолютный, от +X. Поворачивает весь "
     "второй шкив, поэтому спица окна остаётся под рычагом. Параллелограмм "
     "замкнут при LeverAngle = ShoulderAngle + Tube2Angle - 180"),
]
POSE_DERIVED = [
    ("RodAX",        "App::PropertyLength", "Поза: тяга",
     "{V}.LeverLen * cos(({P}.LeverAngle - {P}.ShoulderAngle))",
     "X отверстия рычага в СК руки (Part_Tube) (= первый палец тяги)"),
    ("RodAY",        "App::PropertyLength", "Поза: тяга",
     "{V}.LeverLen * sin(({P}.LeverAngle - {P}.ShoulderAngle))", "Y отверстия рычага"),
    ("RodBX",        "App::PropertyLength", "Поза: тяга",
     "{V}.PivotX - {V}.LeverLen * cos({P}.Tube2Angle)",
     "X пальца на шарнире тяги: вылет LeverLen от оси локтя, повёрнутый "
     "на Tube2Angle"),
    ("RodBY",        "App::PropertyLength", "Поза: тяга",
     "-{V}.LeverLen * sin({P}.Tube2Angle)", "Y пальца на шарнире тяги"),
    ("RodLen",       "App::PropertyLength", "Поза: тяга",
     "sqrt((({P}.RodBX - {P}.RodAX) ^ 2 + ({P}.RodBY - {P}.RodAY) ^ 2)"
     " / 1mm^2) * 1mm",
     "МЕЖЦЕНТРОВОЕ тяги. При замкнутом параллелограмме равно PivotX"),
    ("RodAngle",     "App::PropertyAngle",  "Поза: тяга",
     "atan2({P}.RodBY - {P}.RodAY; {P}.RodBX - {P}.RodAX)",
     "Куда смотрит тяга. Считается из обоих углов, поэтому тяга сама "
     "поворачивается за рычагом и предплечьем"),
]
POSE_MOVED = [n for n, *_ in POSE_INPUTS + POSE_DERIVED]


# ---------------------------------------------------------------------------
def pick_doc():
    act = App.ActiveDocument
    if act is not None and act.getObject(BODY_NAME) is not None:
        return act
    for d in App.listDocuments().values():
        if d.getObject(BODY_NAME) is not None:
            return d
    raise RuntimeError("не нашёл документ с телом " + BODY_NAME)


def ensure_varset(doc):
    """Создать VarSet или дополнить существующий, НЕ затирая значения пользователя."""
    vs = doc.getObject(VS_NAME)
    if vs is None:
        vs = doc.addObject("App::VarSet", VS_NAME)
        vs.Label = "Drive"
        created = True
    else:
        created = False

    for name, typ, grp, default, doc_str in INPUTS:
        if not hasattr(vs, name):
            vs.addProperty(typ, name, grp, doc_str)
            setattr(vs, name, default)

    for name, typ, grp, expr, doc_str in DERIVED:
        if not hasattr(vs, name):
            vs.addProperty(typ, name, grp, doc_str)
        # выражение переустанавливаем всегда — формула принадлежит макросу
        vs.setExpression(name, expr.format(V=VS_NAME, P=POSE_NAME))
    # пересчёт ОДИН раз в конце, а не после каждого выражения: на двух телах
    # со 120 зубьями полный пересчёт идёт минуты, и сорок пересчётов подряд
    # вешали FreeCAD наглухо. Порядок в DERIVED всё равно обязателен —
    # свойство должно существовать раньше ссылок на него, а значение для
    # setExpression не нужно.
    doc.recompute()
    return vs, created


def ensure_pose(doc):
    """VarSet позы «Poza»: создать/дополнить, НЕ затирая значения. Если
    документ старый (углы и тяга жили в Drive) — перенести значения,
    переписать все выражения с Drive.X на Poza.X и убрать X из Drive.
    Вызывать ДО ensure_varset."""
    vs = doc.getObject(VS_NAME)
    ps = doc.getObject(POSE_NAME)
    if ps is None:
        ps = doc.addObject("App::VarSet", POSE_NAME)
        ps.Label = "Поза"
    for name, typ, grp, default, doc_str in POSE_INPUTS:
        if not hasattr(ps, name):
            ps.addProperty(typ, name, grp, doc_str)
            old = getattr(vs, name, None) if vs is not None else None
            setattr(ps, name, old if old is not None else default)
    for name, typ, grp, expr, doc_str in POSE_DERIVED:
        if not hasattr(ps, name):
            ps.addProperty(typ, name, grp, doc_str)
        ps.setExpression(name, expr.format(V=VS_NAME, P=POSE_NAME))
    if vs is not None and any(hasattr(vs, n) for n in POSE_MOVED):
        # сначала перепривязать ВСЕ ссылки, потом удалять: сломанное
        # выражение отравляет весь документ
        pat = re.compile(r"\b%s\.(%s)\b" % (VS_NAME, "|".join(POSE_MOVED)))
        n_ex = 0
        for o in doc.Objects:
            if o is vs or o is ps:
                continue
            for path, ex in list(o.ExpressionEngine):
                nex = pat.sub(POSE_NAME + r".\1", ex)
                if nex != ex:
                    o.setExpression(path.lstrip("."), nex)
                    n_ex += 1
        for n in POSE_MOVED:
            if hasattr(vs, n):
                vs.setExpression(n, None)
        for n in POSE_MOVED:
            if hasattr(vs, n):
                vs.removeProperty(n)
        print("поза перенесена из %s в %s: выражений %d" % (VS_NAME, POSE_NAME, n_ex))
    return ps


def upgrade_pose(doc=None):
    """Перевести ГОТОВЫЙ документ на VarSet позы без пересборки: перенести
    углы из Drive в Poza и привязать к ShoulderAngle шкив 1, крышку
    хомута, его винты и трубу руки (то же, что делают build_* при сборке
    с нуля). Пересчёт — один, в конце."""
    doc = doc or pick_doc()
    ps = ensure_pose(doc)
    for n in (BODY_NAME, CAP_NAME, TUBE_PART):
        o = doc.getObject(n)
        if o is not None:
            setx(o, "Placement.Rotation.Angle", "{P}.ShoulderAngle")
    for o in doc.Objects:
        if not o.Name.startswith("HW_"):
            continue
        ex = dict((k.lstrip("."), v) for k, v in o.ExpressionEngine)
        bx, by = ex.get("Placement.Base.x", ""), ex.get("Placement.Base.y", "")
        if "ShoulderAngle" in bx or not bx:
            continue
        setx(o, "Placement.Base.x", "(%s) * cos({P}.ShoulderAngle) - (%s) * sin({P}.ShoulderAngle)" % (bx, by))
        setx(o, "Placement.Base.y", "(%s) * sin({P}.ShoulderAngle) + (%s) * cos({P}.ShoulderAngle)" % (bx, by))
        setx(o, "Placement.Rotation.Angle", "{P}.ShoulderAngle")
    doc.recompute()
    return ps


def show_tip(body):
    """Сделать видимой только текущую Tip-фичу тела.

    Тело PartDesign рисует в 3D именно Tip, и видимость хранится у фичи,
    а не у тела. Если удалить фичу, которая была Tip (например
    забытое скругление), новая Tip остаётся невидимой — тело исчезает из
    вида, хотя Body.Visibility = True и форма на месте. Выглядит как
    «деталь пропала».
    """
    if not App.GuiUp:
        return
    for f in body.Group:
        f.ViewObject.Visibility = (f is body.Tip)


def setx(obj, prop, expr):
    obj.setExpression(prop, expr.format(V=VS_NAME, P=POSE_NAME))


def add(doc, body, kind, name, exprs=None, rot=None, **props):
    """Добавить примитив PartDesign в конец цепочки тела."""
    f = doc.addObject("PartDesign::" + kind, name)
    f.BaseFeature = body.Tip
    body.addObject(f)
    for k, v in props.items():
        setattr(f, k, v)
    if rot is not None:
        pl = f.Placement
        pl.Rotation = rot
        f.Placement = pl
    for k, v in (exprs or {}).items():
        setx(f, k, v)
    body.Tip = f
    return f


def wipe(doc, body):
    body.Tip = None
    for n in reversed([o.Name for o in list(body.Group)]):
        if doc.getObject(n) is not None:
            doc.removeObject(n)
    doc.recompute()


ROT_X = App.Rotation(App.Vector(0, 1, 0), 90)   # ось примитива Z -> глобальный X
ROT_Y = App.Rotation(App.Vector(1, 0, 0), -90)  # ось примитива Z -> глобальный Y


def purge_orphans(doc):
    """Снести фичи, оставшиеся без тела после прежних прогонов.

    Осиротевшие фичи PartDesign сцеплены через BaseFeature и в дереве
    показывают друг друга как детей, поэтому в RootObjects видно только
    хвост цепочки — снимать приходится слоями, пока не кончатся.
    """
    for _ in range(50):
        owned = set()
        for o in doc.Objects:
            if o.TypeId == "PartDesign::Body":
                owned.update(x.Name for x in o.Group)
        doomed = [o.Name for o in doc.Objects
                  if o.Name.startswith(("K_", "P_", "Q_", "S_", "T_",
                                                   "Rod_", "RdC_", "Tg_")) and o.Name not in owned]
        if not doomed:
            return
        for n in doomed:
            if doc.getObject(n) is not None:
                doc.removeObject(n)
        doc.recompute()


def build_pulley(doc, body):
    wipe(doc, body)
    setx(body, "Placement.Rotation.Angle", "{P}.ShoulderAngle")     # шкив 1 = плечо
    zax = [o for o in body.Origin.OriginFeatures if o.Name.startswith("Z_Axis")][0]

    add(doc, body, "AdditiveCylinder", "P_Flange1",
        {"Radius": "{V}.FlangeD / 2", "Height": "{V}.FlangeThk"})
    add(doc, body, "AdditiveCylinder", "P_Rim",
        {"Radius": "{V}.TipD / 2", "Height": "{V}.RimH",
         "Placement.Base.z": "{V}.FlangeThk"})
    add(doc, body, "AdditiveCylinder", "P_Flange2",
        {"Radius": "{V}.FlangeD / 2", "Height": "{V}.FlangeThk",
         "Placement.Base.z": "{V}.FlangeThk + {V}.RimH"})

    # --- окна облегчения (как в референсе: 3 выреза между спицами) ---
    # сектор режется насквозь, затем ступица возвращается сплошным диском;
    # фаза подобрана так, чтобы спица всегда приходилась под седло руки
    win = add(doc, body, "SubtractiveCylinder", "P_Window",
              {"Radius": "{V}.WindowRout", "Height": "{V}.PulleyH + 2 mm",
               "Angle": "{V}.WindowAngle",
               "Placement.Base.z": "-1 mm",
               "Placement.Rotation.Angle": "{V}.WindowPhase"},
              rot=App.Rotation(App.Vector(0, 0, 1), 1))
    wpat = doc.addObject("PartDesign::PolarPattern", "P_Windows")
    wpat.BaseFeature = body.Tip
    body.addObject(wpat)
    wpat.Originals = [win]
    wpat.Axis = (zax, [""])
    wpat.Angle = 360.0
    wpat.Mode = "Extent"
    body.Tip = wpat
    setx(wpat, "Occurrences", "{V}.WindowCount")
    add(doc, body, "AdditiveCylinder", "P_Hub",
        {"Radius": "{V}.WindowRin", "Height": "{V}.PulleyH"})

    # --- седло под трубу (до сверловок, чтобы отверстия прошли и через него) ---
    add(doc, body, "AdditiveBox", "P_Saddle",
        {"Length": "{V}.ClampLen", "Width": "2 * {V}.SaddleHalfW",
         "Height": "{V}.SaddleH",
         "Placement.Base.x": "{V}.ClampStartR",
         "Placement.Base.y": "-{V}.SaddleHalfW",
         "Placement.Base.z": "{V}.PulleyH"})
    # полукруглый жёлоб: цилиндр по оси X + вырез всего, что над ним
    add(doc, body, "SubtractiveCylinder", "P_TubeGroove",
        {"Radius": "{V}.TubeOD / 2", "Height": "{V}.ClampLen + 20 mm",
         "Placement.Base.x": "{V}.ClampStartR - 10 mm",
         "Placement.Base.z": "{V}.TubeAxisZ"}, rot=ROT_X)
    add(doc, body, "SubtractiveBox", "P_TubeOpen",
        {"Length": "{V}.ClampLen + 20 mm", "Width": "{V}.TubeOD", "Height": "20 mm",
         "Placement.Base.x": "{V}.ClampStartR - 10 mm",
         "Placement.Base.y": "-{V}.TubeOD / 2",
         "Placement.Base.z": "{V}.TubeAxisZ"})

    # --- зубья ---
    groove = add(doc, body, "SubtractiveCylinder", "P_Groove",
                 {"Radius": "{V}.ToothR", "Height": "{V}.RimH",
                  "Placement.Base.x": "{V}.PitchD2 / 2 - {V}.ToothOffset",
                  "Placement.Base.z": "{V}.FlangeThk"})
    pat = doc.addObject("PartDesign::PolarPattern", "P_Teeth")
    pat.BaseFeature = body.Tip
    body.addObject(pat)
    pat.Originals = [groove]
    pat.Axis = (zax, [""])
    pat.Angle = 360.0
    pat.Mode = "Extent"
    body.Tip = pat
    setx(pat, "Occurrences", "{V}.DrivenTeeth")

    # --- отверстия ---
    add(doc, body, "SubtractiveCylinder", "P_Bore",
        {"Radius": "{V}.ShaftHoleD / 2", "Height": "{V}.PulleyH + 2 mm",
         "Placement.Base.z": "-1 mm"})
    add(doc, body, "SubtractiveCylinder", "P_Seat",
        {"Radius": "{V}.BrgOD / 2", "Height": "{V}.BrgW"})

    # --- крепёж хомута: сквозное отверстие сверху + паз под гайку M3 ---
    # винт идёт с крышки вниз и затягивается в гайку, лежащую в пазу седла.
    # Гайка заводится сбоку, тянущее усилие держит потолок паза (5+ мм),
    # пол паза нужен только чтобы гайка не выпала.
    for i, (sx, sy) in enumerate([("ScrewX1", "+"), ("ScrewX1", "-"),
                                  ("ScrewX2", "+"), ("ScrewX2", "-")]):
        plus = (sy == "+")
        ey = ("" if plus else "-") + "{V}.ScrewY"
        # ближняя к центру пара сверлится насквозь через весь шкив: винт
        # может выходить за гайку, длина винта перестаёт быть критичной.
        # Дальняя пара висит за фланцем, сверлить там нечего.
        skvoz = (sx == "ScrewX1")
        z0 = "-1 mm" if skvoz else "{V}.PulleyH - 2 mm"
        hh = ("{V}.TubeAxisZ + 2 mm" if skvoz
              else "{V}.TubeAxisZ - {V}.PulleyH + 2 mm")
        add(doc, body, "SubtractiveCylinder", "P_Screw%d" % (i + 1),
            {"Radius": "({V}.ScrewM + 0.4 mm) / 2",
             "Height": hh,
             "Placement.Base.x": "{V}." + sx,
             "Placement.Base.y": ey,
             "Placement.Base.z": z0})
        add(doc, body, "SubtractivePrism", "P_Nut%d" % (i + 1),
            {"Circumradius": "{V}.NutCircumR", "Height": "{V}.NutThk",
             "Placement.Base.x": "{V}." + sx,
             "Placement.Base.y": ey,
             "Placement.Base.z": "{V}.NutZ"},
            rot=App.Rotation(App.Vector(0, 0, 1), 30), Polygon=6)
        ybase = ("{V}.ScrewY" if plus else "-({V}.SaddleHalfW + 1 mm)")
        add(doc, body, "SubtractiveBox", "P_NutSlot%d" % (i + 1),
            {"Length": "{V}.NutAF",
             "Width": "{V}.SaddleHalfW + 1 mm - {V}.ScrewY",
             "Height": "{V}.NutThk",
             "Placement.Base.x": "{V}." + sx + " - {V}.NutAF / 2",
             "Placement.Base.y": ybase,
             "Placement.Base.z": "{V}.NutZ"})

    body.Label = PULLEY_LABEL
    doc.recompute()
    show_tip(body)
    return body


def build_cap(doc, part):
    old = doc.getObject(CAP_NAME)
    if old is not None:
        # removeObject на теле НЕ удаляет его фичи — они осиротеют в корне
        # документа. Сначала вычищаем содержимое, только потом само тело.
        wipe(doc, old)
        doc.removeObject(old.Name)
        doc.recompute()
    purge_orphans(doc)
    body = doc.addObject("PartDesign::Body", CAP_NAME)
    part.addObject(body)
    body.Label = CAP_LABEL
    setx(body, "Placement.Rotation.Angle", "{P}.ShoulderAngle")     # крышка — с плечом

    add(doc, body, "AdditiveBox", "K_Body",
        {"Length": "{V}.ClampLen", "Width": "2 * {V}.SaddleHalfW",
         "Height": "{V}.CapThk",
         "Placement.Base.x": "{V}.ClampStartR",
         "Placement.Base.y": "-{V}.SaddleHalfW",
         "Placement.Base.z": "{V}.TubeAxisZ"})
    add(doc, body, "SubtractiveCylinder", "K_Groove",
        {"Radius": "{V}.TubeOD / 2", "Height": "{V}.ClampLen + 20 mm",
         "Placement.Base.x": "{V}.ClampStartR - 10 mm",
         "Placement.Base.z": "{V}.TubeAxisZ"}, rot=ROT_X)
    for i, (sx, sy) in enumerate([("ScrewX1", "+"), ("ScrewX1", "-"),
                                  ("ScrewX2", "+"), ("ScrewX2", "-")]):
        s = ("" if sy == "+" else "-") + "{V}.ScrewY"
        add(doc, body, "SubtractiveCylinder", "K_Hole%d" % (i + 1),
            {"Radius": "({V}.ScrewM + 0.4 mm) / 2", "Height": "{V}.CapThk + 2 mm",
             "Placement.Base.x": "{V}." + sx, "Placement.Base.y": s,
             "Placement.Base.z": "{V}.TubeAxisZ - 1 mm"})
        add(doc, body, "SubtractiveCylinder", "K_Cbore%d" % (i + 1),
            {"Radius": "{V}.ScrewM", "Height": "{V}.CapWall",
             "Placement.Base.x": "{V}." + sx, "Placement.Base.y": s,
             "Placement.Base.z": "{V}.TubeAxisZ + {V}.CapThk - {V}.CapWall"})
    doc.recompute()
    show_tip(body)
    return body


def build_pulley2(doc, part):
    """Второй ведомый шкив: та же передача, без хомута, с рычагом.

    Сидит на проставке над первым шкивом. Венец и диаметры считаются из
    тех же переменных, что у первого, то есть передача совпадает
    автоматически. Рычаг висит ПОД нижним фланцем: внутри фланцев идёт
    ремень, туда лезть нельзя, а снизу свободно.

    Ядро (фланцы/венец/окна/зубья) повторяет build_pulley — специально
    отдельным кодом с префиксом Q_, чтобы правки здесь не трогали
    работающую цепочку первого шкива.
    """
    old = doc.getObject(PUL2_NAME)
    if old is not None:
        wipe(doc, old)
        doc.removeObject(old.Name)
        doc.recompute()
    purge_orphans(doc)
    body = doc.addObject("PartDesign::Body", PUL2_NAME)
    part.addObject(body)
    body.Label = PUL2_LABEL
    zax = [o for o in body.Origin.OriginFeatures if o.Name.startswith("Z_Axis")][0]

    # --- рычаг: утолщение нижнего фланца, верх заподлицо с его верхом ---
    # Верхняя грань рычага = верхняя грань фланца, рост идёт вниз. Внутри
    # фланцев проходит ремень, а под фланцем свободно, поэтому толщину
    # рычага можно менять не оглядываясь на ремень. До центра рычаг не
    # доходит (начинается с LeverR0): снизу в ступицу заходит подшипник.
    add(doc, body, "AdditiveBox", "Q_LeverBar",
        {"Length": "{V}.LeverLen - {V}.LeverR0",
         "Width": "{V}.LeverWidth", "Height": "{V}.LeverThk",
         "Placement.Base.x": "{V}.LeverR0",
         "Placement.Base.y": "-{V}.LeverWidth / 2",
         "Placement.Base.z": "{V}.LeverZ"})
    add(doc, body, "AdditiveCylinder", "Q_LeverTip",
        {"Radius": "{V}.LeverWidth / 2", "Height": "{V}.LeverThk",
         "Placement.Base.x": "{V}.LeverLen",
         "Placement.Base.z": "{V}.LeverZ"})

    # --- шкив: те же выражения, что у первого, только со смещением по z ---
    add(doc, body, "AdditiveCylinder", "Q_Flange1",
        {"Radius": "{V}.FlangeD2 / 2", "Height": "{V}.FlangeThk2",
         "Placement.Base.z": "{V}.Pulley2Z"})
    add(doc, body, "AdditiveCylinder", "Q_Rim",
        {"Radius": "{V}.TipD2 / 2", "Height": "{V}.RimH2",
         "Placement.Base.z": "{V}.Pulley2Z + {V}.FlangeThk2"})
    add(doc, body, "AdditiveCylinder", "Q_Flange2",
        {"Radius": "{V}.FlangeD2 / 2", "Height": "{V}.FlangeThk2",
         "Placement.Base.z": "{V}.Pulley2Z + {V}.FlangeThk2 + {V}.RimH2"})

    win = add(doc, body, "SubtractiveCylinder", "Q_Window",
              {"Radius": "{V}.WindowRout2", "Height": "{V}.PulleyH2 + 2 mm",
               "Angle": "{V}.WindowAngle2",
               "Placement.Base.z": "{V}.Pulley2Z - 1 mm",
               "Placement.Rotation.Angle": "{V}.WindowPhase2"},
              rot=App.Rotation(App.Vector(0, 0, 1), 1))
    wpat = doc.addObject("PartDesign::PolarPattern", "Q_Windows")
    wpat.BaseFeature = body.Tip
    body.addObject(wpat)
    wpat.Originals = [win]
    wpat.Axis = (zax, [""])
    wpat.Angle = 360.0
    wpat.Mode = "Extent"
    body.Tip = wpat
    setx(wpat, "Occurrences", "{V}.WindowCount2")

    add(doc, body, "AdditiveCylinder", "Q_Hub",
        {"Radius": "{V}.WindowRin2", "Height": "{V}.PulleyH2",
         "Placement.Base.z": "{V}.Pulley2Z"})

    groove = add(doc, body, "SubtractiveCylinder", "Q_Groove",
                 {"Radius": "{V}.ToothR", "Height": "{V}.RimH2",
                  "Placement.Base.x": "{V}.PitchDriven2 / 2 - {V}.ToothOffset",
                  "Placement.Base.z": "{V}.Pulley2Z + {V}.FlangeThk2"})
    pat = doc.addObject("PartDesign::PolarPattern", "Q_Teeth")
    pat.BaseFeature = body.Tip
    body.addObject(pat)
    pat.Originals = [groove]
    pat.Axis = (zax, [""])
    pat.Angle = 360.0
    pat.Mode = "Extent"
    body.Tip = pat
    setx(pat, "Occurrences", "{V}.DrivenTeeth2")

    # --- отверстия: ось насквозь через шкив и рычаг, плюс глаз рычага ---
    add(doc, body, "SubtractiveCylinder", "Q_Bore",
        {"Radius": "{V}.ShaftHoleD2 / 2",
         "Height": "{V}.Pulley2Z + {V}.PulleyH2 - {V}.LeverZ + 2 mm",
         "Placement.Base.z": "{V}.LeverZ - 1 mm"})
    # гнездо подшипника открыто ВНИЗ, как у первого шкива; сверху от него
    # остаётся упор толщиной PulleyH - BrgW с отверстием ShaftHoleD
    add(doc, body, "SubtractiveCylinder", "Q_Seat2",
        {"Radius": "{V}.BrgOD2 / 2", "Height": "{V}.BrgW2 + 1 mm",
         "Placement.Base.z": "{V}.BrgZ2 - 1 mm"})
    add(doc, body, "SubtractiveCylinder", "Q_LeverHole",
        {"Radius": "{V}.LeverHoleD / 2", "Height": "{V}.LeverThk + 2 mm",
         "Placement.Base.x": "{V}.LeverLen",
         "Placement.Base.z": "{V}.LeverZ - 1 mm"})
    # зенковка под потайной палец тяги: головка заподлицо с верхом рычага,
    # иначе на краю диапазона она цепляет ветвь ремня 2 (полоса ремня
    # начинается ровно на верхней грани рычага)
    add(doc, body, "SubtractiveCone", "Q_LeverCsk",
        {"Placement.Base.x": "{V}.LeverLen",
         "Placement.Base.z": "{V}.LeverZ + {V}.LeverThk - %s mm" % CSK_H},
        Radius1=CSK_R1, Radius2=CSK_R2 + 0.5, Height=CSK_H + 0.5)

    # рычаг смотрит вдоль +X; направление задаётся поворотом всего тела,
    # поэтому спица окна остаётся ровно под рычагом
    setx(body, "Placement.Rotation.Angle", "{P}.LeverAngle")
    doc.recompute()
    show_tip(body)
    return body


def build_tube(doc):
    """Труба руки — ОТДЕЛЬНЫЙ парт, вставляется в хомут первого шкива.

    Свой контейнер App::Part, чтобы трубу можно было двигать и считать
    отдельной деталью. Его Placement привязан к тем же переменным, что и
    у привода, поэтому труба едет вместе с узлом: по Y на межосевое, по
    Z на плоскость венца.
    """
    old = doc.getObject(TUBE_BODY)
    if old is not None:
        wipe(doc, old)
        doc.removeObject(old.Name)
        doc.recompute()
    purge_orphans(doc)
    part = doc.getObject(TUBE_PART)
    if part is None:
        part = doc.addObject("App::Part", TUBE_PART)
        part.Label = TUBE_PLABEL
    body = doc.addObject("PartDesign::Body", TUBE_BODY)
    part.addObject(body)
    body.Label = TUBE_BLABEL

    add(doc, body, "AdditiveCylinder", "T_Tube",
        {"Radius": "{V}.TubeOD / 2", "Height": "{V}.TubeLen",
         "Placement.Base.x": "{V}.ClampStartR",
         "Placement.Base.z": "{V}.TubeAxisZ"}, rot=ROT_X)
    add(doc, body, "SubtractiveCylinder", "T_Bore",
        {"Radius": "{V}.TubeOD / 2 - {V}.TubeWall",
         "Height": "{V}.TubeLen + 2 mm",
         "Placement.Base.x": "{V}.ClampStartR - 1 mm",
         "Placement.Base.z": "{V}.TubeAxisZ"}, rot=ROT_X)

    setx(part, "Placement.Base.x", "{V}.PulleyAxisX")
    setx(part, "Placement.Base.y", "{V}.ArmAxisY")
    setx(part, "Placement.Base.z", "{V}.BeltPlaneZ - {V}.FlangeThk")
    setx(part, "Placement.Rotation.Angle", "{P}.ShoulderAngle")     # плечо
    doc.recompute()
    show_tip(body)
    return body


def _clamp_screws(doc, body, xs, zbot, through_h, pfx=None):
    """Вертикальные отверстия M3 и пазы под гайки — схема как на шкиве 1.

    Винт идёт сверху через зенковку в крышке и затягивается в гайку,
    лежащую в пазу на нижней грани хомута. Паз открыт вбок, гайка
    заводится сбоку, тянущее усилие держит его потолок.
    """
    pfx = pfx or body.Name[5:8]
    for i, xe in enumerate(xs):
        for sy in ("+", "-"):
            ey = ("" if sy == "+" else "-") + "{V}.ElbowScrewY"
            tag = "%d%s" % (i + 1, "p" if sy == "+" else "m")
            add(doc, body, "SubtractiveCylinder", "%s_Scr%s" % (pfx, tag),
                {"Radius": "({V}.ScrewM + 0.4 mm) / 2", "Height": through_h,
                 "Placement.Base.x": xe, "Placement.Base.y": ey,
                 "Placement.Base.z": zbot + " - 1 mm"})
            add(doc, body, "SubtractivePrism", "%s_Nut%s" % (pfx, tag),
                {"Circumradius": "{V}.NutCircumR", "Height": "{V}.NutThk",
                 "Placement.Base.x": xe, "Placement.Base.y": ey,
                 "Placement.Base.z": zbot + " + {V}.ClampNutLift"},
                rot=App.Rotation(App.Vector(0, 0, 1), 30), Polygon=6)
            ybase = (ey if sy == "+" else "-({V}.ElbowHalfW + 1 mm)")
            add(doc, body, "SubtractiveBox", "%s_Slot%s" % (pfx, tag),
                {"Length": "{V}.NutAF",
                 "Width": "{V}.ElbowHalfW + 1 mm - {V}.ElbowScrewY",
                 "Height": "{V}.NutThk",
                 "Placement.Base.x": xe + " - {V}.NutAF / 2",
                 "Placement.Base.y": ybase,
                 "Placement.Base.z": zbot + " + {V}.ClampNutLift"})


def _clamp_cap(doc, part, name, label, x0, length, like, pfx=None):
    """Прижимная крышка хомута: половина жёлоба сверху плюс зенковки."""
    old = doc.getObject(name)
    if old is not None:
        wipe(doc, old)
        doc.removeObject(old.Name)
        doc.recompute()
    purge_orphans(doc)
    body = doc.addObject("PartDesign::Body", name)
    part.addObject(body)
    body.Label = label
    pfx = pfx or name[5:8]
    add(doc, body, "AdditiveBox", "%s_Body" % pfx,
        {"Length": length, "Width": "2 * {V}.ElbowHalfW", "Height": "{V}.CapThk",
         "Placement.Base.x": x0, "Placement.Base.y": "-{V}.ElbowHalfW"})
    add(doc, body, "SubtractiveCylinder", "%s_Groove" % pfx,
        {"Radius": "{V}.TubeOD / 2", "Height": length + " + 2 mm",
         "Placement.Base.x": x0 + " - 1 mm"}, rot=ROT_X)
    for i, xe in enumerate(like):
        for sy in ("+", "-"):
            ey = ("" if sy == "+" else "-") + "{V}.ElbowScrewY"
            tag = "%d%s" % (i + 1, "p" if sy == "+" else "m")
            add(doc, body, "SubtractiveCylinder", "%s_H%s" % (pfx, tag),
                {"Radius": "({V}.ScrewM + 0.4 mm) / 2", "Height": "{V}.CapThk + 2 mm",
                 "Placement.Base.x": xe, "Placement.Base.y": ey,
                 "Placement.Base.z": "-1 mm"})
            add(doc, body, "SubtractiveCylinder", "%s_C%s" % (pfx, tag),
                {"Radius": "{V}.ScrewM", "Height": "{V}.CapWall",
                 "Placement.Base.x": xe, "Placement.Base.y": ey,
                 "Placement.Base.z": "{V}.CapThk - {V}.CapWall"})
    doc.recompute()
    show_tip(body)
    return body


def build_elbow(doc, part):
    """Локоть: шарнир на подшипнике между первой и второй трубой.

    Два хомута, каждый на винтах M3 по той же схеме, что хомут на шкиве.
    Хомут 1 сидит на торце первой трубы и несёт проушину, хомут 2 держит
    вторую трубу (она проходит его насквозь) и вращается на подшипнике.

    Локальные координаты обоих тел: начало — ОСЬ ШАРНИРА, труба идёт по
    локальному X, её ось на локальном z = 0. Поэтому хомут 2 вместе с
    крышкой и трубой поворачивается простым Placement.Rotation вокруг Z —
    он же проходит ровно через ось шарнира.

    Вторая труба начинается с Tube2X0 ОТ ОСИ ШАРНИРА. Звено мерится до
    ОСИ ПАЛЬЦА ТЯГИ, а она стоит на LeverLen — ровно длина рычага на
    втором шкиве, это и есть условие параллелограмма. Сама труба
    кончается на JointReach раньше пальца: дальше её продолжает планка
    проушины шарнира тяги (см. build_rod_joint).
    """
    for name in (ELBOW_NAME, ELBCAP_NAME, ELBOW2_NAME, ELB2CAP_NAME, TUBE2_NAME):
        old = doc.getObject(name)
        if old is not None:
            wipe(doc, old)
            doc.removeObject(old.Name)
            doc.recompute()
    purge_orphans(doc)

    # ---------- хомут 1: на торце первой трубы, с проушиной ----------
    a = doc.addObject("PartDesign::Body", ELBOW_NAME)
    part.addObject(a)
    a.Label = ELBOW_LABEL
    add(doc, a, "AdditiveBox", "Elb_Block",
        {"Length": "{V}.ElbowEndX + {V}.ElbowGrip", "Width": "2 * {V}.ElbowHalfW",
         "Height": "{V}.ElbowBot",
         "Placement.Base.x": "-({V}.ElbowEndX + {V}.ElbowGrip)",
         "Placement.Base.y": "-{V}.ElbowHalfW",
         "Placement.Base.z": "-{V}.ElbowBot"})
    add(doc, a, "AdditiveCylinder", "Elb_Lug",
        {"Radius": "{V}.PivotLugR", "Height": "{V}.ElbowBot",
         "Placement.Base.z": "-{V}.ElbowBot"})
    add(doc, a, "SubtractiveCylinder", "Elb_Groove",
        {"Radius": "{V}.TubeOD / 2", "Height": "{V}.ElbowGrip + 1 mm",
         "Placement.Base.x": "-({V}.ElbowEndX + {V}.ElbowGrip) - 1 mm"}, rot=ROT_X)
    # буртик под внутренним кольцом: подшипник опирается только им
    add(doc, a, "AdditiveCylinder", "Elb_Boss",
        {"Radius": "2.75 mm", "Height": "{V}.PivotBoss"})
    add(doc, a, "SubtractiveCylinder", "Elb_Pivot",
        {"Radius": "({V}.ScrewM + 0.4 mm) / 2",
         "Height": "{V}.ElbowBot + {V}.PivotBoss + 2 mm",
         "Placement.Base.z": "-{V}.ElbowBot - 1 mm"})
    add(doc, a, "SubtractivePrism", "Elb_PivotNut",
        {"Circumradius": "{V}.NutCircumR", "Height": "{V}.NutThk",
         "Placement.Base.z": "-{V}.ElbowBot + {V}.ClampNutLift"},
        rot=App.Rotation(App.Vector(0, 0, 1), 30), Polygon=6)
    add(doc, a, "SubtractiveBox", "Elb_PivotSlot",
        {"Length": "{V}.NutAF", "Width": "{V}.ElbowHalfW + 1 mm",
         "Height": "{V}.NutThk",
         "Placement.Base.x": "-{V}.NutAF / 2",
         "Placement.Base.z": "-{V}.ElbowBot + {V}.ClampNutLift"})
    _clamp_screws(doc, a, ["-{V}.ElbowScrewX1", "-{V}.ElbowScrewX2"],
                  "-{V}.ElbowBot", "{V}.ElbowBot + 2 mm")
    setx(a, "Placement.Base.x", "{V}.PivotX")
    setx(a, "Placement.Base.z", "{V}.TubeAxisZ")
    doc.recompute()
    show_tip(a)

    acap = _clamp_cap(doc, part, ELBCAP_NAME, ELBCAP_LABEL,
                      "-({V}.ElbowEndX + {V}.ElbowGrip)", "{V}.ElbowGrip",
                      ["-{V}.ElbowScrewX1", "-{V}.ElbowScrewX2"])
    setx(acap, "Placement.Base.x", "{V}.PivotX")
    setx(acap, "Placement.Base.z", "{V}.TubeAxisZ")

    # ---------- хомут 2: на второй трубе, вращается на подшипнике ----------
    b = doc.addObject("PartDesign::Body", ELBOW2_NAME)
    part.addObject(b)
    b.Label = ELBOW2_LABEL
    add(doc, b, "AdditiveBox", "Elb2_Block",
        {"Length": "{V}.ElbowGrip", "Width": "2 * {V}.ElbowHalfW",
         "Height": "{V}.ElbowBot",
         "Placement.Base.x": "-{V}.ElbowGrip / 2",
         "Placement.Base.y": "-{V}.ElbowHalfW",
         "Placement.Base.z": "-{V}.ElbowBot"})
    add(doc, b, "AdditiveCylinder", "Elb2_Lug",
        {"Radius": "{V}.PivotLugR", "Height": "{V}.Elbow2Bot",
         "Placement.Base.z": "-{V}.Elbow2Bot"})
    add(doc, b, "SubtractiveCylinder", "Elb2_Groove",
        {"Radius": "{V}.TubeOD / 2", "Height": "{V}.ElbowGrip + 2 mm",
         "Placement.Base.x": "-{V}.ElbowGrip / 2 - 1 mm"}, rot=ROT_X)
    add(doc, b, "SubtractiveCylinder", "Elb2_Seat",
        {"Radius": "{V}.PivotBrgOD / 2", "Height": "{V}.PivotBrgW",
         "Placement.Base.z": "-{V}.Elbow2Bot"})
    add(doc, b, "SubtractiveCylinder", "Elb2_HeadC",
        {"Radius": "{V}.ScrewM", "Height": "{V}.PivotHeadC",
         "Placement.Base.z": "-{V}.Elbow2Bot + {V}.PivotBrgW"})
    # отверстие под шестигранный ключ 2.5 над головкой винта шарнира: без
    # него головка заперта в глухом кармане и винт не затянуть. Ключ
    # проходит до того, как в хомут легла труба 2 (порядок сборки).
    add(doc, b, "SubtractiveCylinder", "Elb2_KeyHole",
        {"Radius": "1.75 mm", "Height": "{V}.Elbow2Bot + 1 mm",
         "Placement.Base.z": "-{V}.Elbow2Bot + {V}.PivotBrgW"})
    _clamp_screws(doc, b, ["{V}.Elbow2ScrewX", "-{V}.Elbow2ScrewX"],
                  "-{V}.ElbowBot", "{V}.ElbowBot + 2 mm")
    setx(b, "Placement.Base.x", "{V}.PivotX")
    setx(b, "Placement.Base.z", "{V}.Tube2Z")
    setx(b, "Placement.Rotation.Angle", "{P}.Tube2Angle")
    doc.recompute()
    show_tip(b)

    bcap = _clamp_cap(doc, part, ELB2CAP_NAME, ELB2CAP_LABEL,
                      "-{V}.ElbowGrip / 2", "{V}.ElbowGrip",
                      ["{V}.Elbow2ScrewX", "-{V}.Elbow2ScrewX"])
    setx(bcap, "Placement.Base.x", "{V}.PivotX")
    setx(bcap, "Placement.Base.z", "{V}.Tube2Z")
    setx(bcap, "Placement.Rotation.Angle", "{P}.Tube2Angle")

    # ---------- вторая труба, в том же локальном фрейме что хомут 2 ----------
    t2 = doc.addObject("PartDesign::Body", TUBE2_NAME)
    part.addObject(t2)
    t2.Label = TUBE2_LABEL
    add(doc, t2, "AdditiveCylinder", "U_Tube",
        {"Radius": "{V}.TubeOD / 2", "Height": "{V}.Tube2Full",
         "Placement.Base.x": "{V}.Tube2X0"}, rot=ROT_X)
    add(doc, t2, "SubtractiveCylinder", "U_Bore",
        {"Radius": "{V}.TubeOD / 2 - {V}.TubeWall",
         "Height": "{V}.Tube2Full + 2 mm",
         "Placement.Base.x": "{V}.Tube2X0 - 1 mm"}, rot=ROT_X)
    setx(t2, "Placement.Base.x", "{V}.PivotX")
    setx(t2, "Placement.Base.z", "{V}.Tube2Z")
    setx(t2, "Placement.Rotation.Angle", "{P}.Tube2Angle")
    doc.recompute()
    show_tip(t2)
    return a, acap, b, bcap, t2


def build_rod_joint(doc, part):
    """Шарнир тяги на свободном конце второй трубы.

    Проушина лежит РОВНО в полосе рычага второго шкива
    (z LeverZ..LeverZ + LeverThk), поэтому тяга между ними — плоская
    планка с двумя отверстиями Ø LeverHoleD, а не Z-образная.

    Ось пальца стоит на LeverLen от оси шарнира локтя: вылет предплечья
    равен рычагу — это и есть условие параллелограмма. Поэтому труба 2
    кончается на JointReach раньше пальца, а пролёт до него закрывает
    планка проушины; иначе планку пришлось бы вести внутри трубы.

    Хомут садится на конец трубы как остальные: низ + крышка на винтах
    M3 с гайками в пазах. Торцевая стенка JointWall заглушает его с
    конца — в неё планка и входит, поэтому стык объёмный, а не по
    касательной.

    Локальный фрейм тот же, что у хомута 2 и трубы 2: начало — ось
    шарнира локтя, труба по локальному X, её ось на z = 0. Значит хомут
    поворачивается вместе с предплечьем (Tube2Angle).
    """
    old = doc.getObject(JOINT_NAME)
    if old is not None:
        wipe(doc, old)
        doc.removeObject(old.Name)
        doc.recompute()
    purge_orphans(doc)
    j = doc.addObject("PartDesign::Body", JOINT_NAME)
    part.addObject(j)
    j.Label = JOINT_LABEL
    xs = ["{V}.JointMidX + {V}.JointScrewX", "{V}.JointMidX - {V}.JointScrewX"]

    add(doc, j, "AdditiveBox", "Rod_Block",
        {"Length": "{V}.JointGrip + {V}.JointWall",
         "Width": "2 * {V}.ElbowHalfW", "Height": "{V}.ElbowBot",
         "Placement.Base.x": "{V}.Tube2X0 - {V}.JointWall",
         "Placement.Base.y": "-{V}.ElbowHalfW",
         "Placement.Base.z": "-{V}.ElbowBot"})
    add(doc, j, "AdditiveBox", "Rod_Bar",
        {"Length": "{V}.JointReach", "Width": "{V}.LeverWidth",
         "Height": "{V}.LeverThk",
         "Placement.Base.x": "-{V}.LeverLen",
         "Placement.Base.y": "-{V}.LeverWidth / 2",
         "Placement.Base.z": "{V}.JointPlateZ"})
    add(doc, j, "AdditiveCylinder", "Rod_Eye",
        {"Radius": "{V}.JointEyeR", "Height": "{V}.LeverThk",
         "Placement.Base.x": "-{V}.LeverLen",
         "Placement.Base.z": "{V}.JointPlateZ"})
    # жёлоб режется ПОСЛЕ планки: там, где планка попала в зону трубы,
    # материал уходит, и труба садится в хомут без натяга
    add(doc, j, "SubtractiveCylinder", "Rod_Groove",
        {"Radius": "{V}.TubeOD / 2", "Height": "{V}.JointGrip + 1 mm",
         "Placement.Base.x": "{V}.Tube2X0"}, rot=ROT_X)
    _clamp_screws(doc, j, xs, "-{V}.ElbowBot", "{V}.ElbowBot + 2 mm", pfx="Rod")
    add(doc, j, "SubtractiveCylinder", "Rod_Hole",
        {"Radius": "{V}.LeverHoleD / 2", "Height": "{V}.LeverThk + 2 mm",
         "Placement.Base.x": "-{V}.LeverLen",
         "Placement.Base.z": "{V}.JointPlateZ - 1 mm"})
    add(doc, j, "SubtractiveCone", "Rod_Csk",
        {"Placement.Base.x": "-{V}.LeverLen",
         "Placement.Base.z": "{V}.JointPlateZ + {V}.LeverThk - %s mm" % CSK_H},
        Radius1=CSK_R1, Radius2=CSK_R2 + 0.5, Height=CSK_H + 0.5)
    setx(j, "Placement.Base.x", "{V}.PivotX")
    setx(j, "Placement.Base.z", "{V}.Tube2Z")
    setx(j, "Placement.Rotation.Angle", "{P}.Tube2Angle")
    doc.recompute()
    show_tip(j)

    jcap = _clamp_cap(doc, part, JNTCAP_NAME, JNTCAP_LABEL,
                      "{V}.Tube2X0", "{V}.JointGrip", xs, pfx="RdC")
    setx(jcap, "Placement.Base.x", "{V}.PivotX")
    setx(jcap, "Placement.Base.z", "{V}.Tube2Z")
    setx(jcap, "Placement.Rotation.Angle", "{P}.Tube2Angle")
    return j, jcap


def build_rod(doc, part, vs):
    """Тяга параллелограмма: планка между рычагом шкива 2 и шарниром на
    конце предплечья, плюс два пальца M3.

    Тело строится вдоль своего локального +X от первого пальца, а оба
    конца находит само: `RodAX/RodAY` — отверстие рычага, `RodBX/RodBY` —
    палец шарнира тяги, `RodLen` — расстояние между ними, `RodAngle` —
    направление. Поэтому при повороте `LeverAngle` или `Tube2Angle` тяга
    поворачивается и растягивается сама, оставаясь на своих пальцах.

    Тяга идёт СНИЗУ: сверху и рычаг, и проушина закрыты (над рычагом
    фланец шкива, над проушиной крышка хомута), а снизу свободно. Верх
    тяги = низ рычага, то есть скользящий контакт — так плоские тяги и
    работают.

    Палец: винт M3 сверху через рычаг/проушину и тягу, гайка под тягой.
    """
    old = doc.getObject(ROD_NAME)
    if old is not None:
        wipe(doc, old)
        doc.removeObject(old.Name)
        doc.recompute()
    for o in list(doc.Objects):
        if o.Name.startswith("RD_"):
            doc.removeObject(o.Name)
    doc.recompute()
    purge_orphans(doc)

    b = doc.addObject("PartDesign::Body", ROD_NAME)
    part.addObject(b)
    b.Label = ROD_LABEL
    add(doc, b, "AdditiveBox", "Tg_Bar",
        {"Length": "{P}.RodLen", "Width": "{V}.RodBarW",
         "Height": "{V}.RodThk", "Placement.Base.y": "-{V}.RodBarW / 2"})
    add(doc, b, "AdditiveCylinder", "Tg_EyeA",
        {"Radius": "{V}.RodEyeR", "Height": "{V}.RodThk"})
    add(doc, b, "AdditiveCylinder", "Tg_EyeB",
        {"Radius": "{V}.RodEyeR", "Height": "{V}.RodThk",
         "Placement.Base.x": "{P}.RodLen"})
    # гнёзда 623ZZ насквозь: подшипник запрессован заподлицо (RodThk = его
    # ширина), внутреннее кольцо зажато пальцем между втулкой и шайбой
    add(doc, b, "SubtractiveCylinder", "Tg_HoleA",
        {"Radius": "{V}.PivotBrgOD / 2", "Height": "{V}.RodThk + 2 mm",
         "Placement.Base.z": "-1 mm"})
    add(doc, b, "SubtractiveCylinder", "Tg_HoleB",
        {"Radius": "{V}.PivotBrgOD / 2", "Height": "{V}.RodThk + 2 mm",
         "Placement.Base.x": "{P}.RodLen", "Placement.Base.z": "-1 mm"})
    setx(b, "Placement.Base.x", "{P}.RodAX")
    setx(b, "Placement.Base.y", "{P}.RodAY")
    setx(b, "Placement.Base.z", "{V}.RodZ")
    setx(b, "Placement.Rotation.Angle", "{P}.RodAngle")
    doc.recompute()
    show_tip(b)

    # пальцы: потайной винт сверху заподлицо с рычагом/проушиной, втулка,
    # подшипник в тяге, шайба по внутреннему кольцу, гайка снизу
    need = (vs.LeverThk.Value + vs.RodStandoff.Value + vs.RodThk.Value
            + WASHER_T + NUT_H)
    length = next((L for L in CSK_LENGTHS if L >= need + 1.0), CSK_LENGTHS[-1])
    brg = lib_rigid(LIB_PIVOT_BRG)
    if brg is not None:
        brg = brg.copy()
        brg.Placement = App.Placement()       # см. build_pivot_hw
    nut = lib_shape(LIB_NUT)
    parts_ = (
        ("Vint", "Палец_тяги_M3x%d_%%s (ISO10642)" % length, csk_screw(length),
         "{V}.LeverZ + {V}.LeverThk", (0.30, 0.32, 0.35)),
        ("Vtul", "Втулка_тяги_%%s_Ø%.1f/Ø3.2x%.0f" % (STANDOFF_OD, vs.RodStandoff.Value),
         tube_shape(STANDOFF_OD, 3.2, vs.RodStandoff.Value),
         "{V}.LeverZ - {V}.RodStandoff", (0.80, 0.62, 0.20)),
        ("Brg", "Подшипник_тяги_623ZZ_%s", brg, "{V}.RodZ", (0.62, 0.64, 0.67)),
        ("Shayba", "Шайба_тяги_M3_%s (DIN125)",
         tube_shape(WASHER_OD, 3.2, WASHER_T),
         "{V}.RodZ - %s mm" % WASHER_T, (0.70, 0.70, 0.72)),
        ("Gayka", "Гайка_тяги_M3_%s", nut,
         "{V}.RodZ - %s mm - %s mm" % (WASHER_T, NUT_H), (0.55, 0.56, 0.58)),
    )
    made = 0
    for tag, xe, ye in (("A", "{P}.RodAX", "{P}.RodAY"),
                        ("B", "{P}.RodBX", "{P}.RodBY")):
        for kind, label, shape, zexpr, color in parts_:
            if shape is None:
                print("  тяга: нет детали %s, пропускаю" % label)
                continue
            o = doc.addObject("Part::Feature", "RD_%s%s" % (kind, tag))
            o.Shape = shape.copy()
            o.Label = label % tag
            part.addObject(o)
            setx(o, "Placement.Base.x", xe)
            setx(o, "Placement.Base.y", ye)
            setx(o, "Placement.Base.z", zexpr)
            if App.GuiUp:
                o.ViewObject.ShapeColor = color
                o.ViewObject.DiffuseColor = [color]
            made += 1
    doc.recompute()
    return b, length, made


# --- покупной крепёж, которого нет в библиотеке: строим по стандарту ---
CSK_R1, CSK_R2, CSK_H = 1.6, 3.36, 1.86       # ISO 10642 M3: dk 6.72, k 1.86
CSK_LENGTHS = (8, 10, 12, 16, 18, 20, 25)     # L — вместе с головкой
WASHER_OD, WASHER_T = 7.0, 0.5                # DIN 125 M3 (по внутреннему кольцу 623)
STANDOFF_OD = 5.5                             # меньше Ø7.8 наружного кольца 623
NUT_H = 2.4                                   # ISO 4032 M3


def csk_screw(L):
    """ISO 10642 M3xL: верх головки на z = 0, винт смотрит вниз."""
    import Part
    head = Part.makeCone(CSK_R1, CSK_R2, CSK_H, App.Vector(0, 0, -CSK_H))
    shank = Part.makeCylinder(1.5, L - CSK_H, App.Vector(0, 0, -L))
    hexs = Part.makePolygon([App.Vector(1.27 * math.cos(math.radians(a)),
                                        1.27 * math.sin(math.radians(a)), 0)
                             for a in range(0, 361, 60)])
    key = Part.Face(hexs).extrude(App.Vector(0, 0, -1.2))
    return head.fuse(shank).cut(key).removeSplitter()


def tube_shape(od, idd, h):
    """Втулка/шайба: низ на z = 0."""
    import Part
    return Part.makeCylinder(od / 2.0, h).cut(Part.makeCylinder(idd / 2.0, h))


LIB_PIVOT_BRG = "Mechanical Parts/Bearings/623ZZ_Ball_Bearing.fcstd"


def build_pivot_hw(doc, part, vs):
    """Подшипник шарнира, его винт и гайка.

    Винт идёт СВЕРХУ: головка прижимает внутреннее кольцо к проушине
    хомута 1, гайка сидит в пазу под проушиной. Наружное кольцо
    запрессовано в хомут 2, поэтому хомут 2 свободно вращается, а винт
    ничего к нему не притягивает.
    """
    for o in list(doc.Objects):
        if o.Name.startswith("PV_"):
            doc.removeObject(o.Name)
    doc.recompute()
    brg = lib_rigid(LIB_PIVOT_BRG)
    if brg is not None:
        # у 623ZZ собственный Placement разворачивает ось на Y; сырая
        # геометрия смотрит ровно по Z и лежит в z 0..PivotBrgW — это и
        # нужно для вертикального шарнира
        brg = brg.copy()
        brg.Placement = App.Placement()
    need = (vs.PivotBrgW.Value + vs.PivotBoss.Value + vs.ElbowBot.Value
            - vs.ClampNutLift.Value)
    length = next((L for L in LIB_SCREW_LENGTHS if L >= need), LIB_SCREW_LENGTHS[-1])
    screw = lib_shape(LIB_SCREWS % length)
    nut = lib_shape(LIB_NUT)
    made = 0
    for name, label, shape, zexpr, color in (
            ("PV_Brg", "Подшипник_623ZZ_шарнир", brg,
             "{V}.TubeAxisZ + {V}.PivotBoss", (0.62, 0.64, 0.67)),
            ("PV_Screw", "Винт_шарнира_M3x%d" % length, screw,
             "{V}.TubeAxisZ + {V}.PivotBoss + {V}.PivotBrgW", (0.30, 0.32, 0.35)),
            ("PV_Nut", "Гайка_шарнира_M3", nut,
             "{V}.TubeAxisZ - {V}.ElbowBot + {V}.ClampNutLift", (0.55, 0.56, 0.58))):
        if shape is None:
            print("  шарнир: нет детали для %s, пропускаю" % label)
            continue
        o = doc.addObject("Part::Feature", name)
        o.Shape = shape.copy()
        o.Label = label
        part.addObject(o)
        setx(o, "Placement.Base.x", "{V}.PivotX")
        setx(o, "Placement.Base.z", zexpr)
        if App.GuiUp:
            o.ViewObject.ShapeColor = color
            o.ViewObject.DiffuseColor = [color]
        made += 1
    doc.recompute()
    return made, length


# хомуты локтя: (тег, локальные X винтов, база Z тела, угол поворота тела)
ELBOW_CLAMPS = (
    ("E1", ("-{V}.ElbowScrewX1", "-{V}.ElbowScrewX2"), "{V}.TubeAxisZ", "0 deg"),
    ("E2", ("{V}.Elbow2ScrewX", "-{V}.Elbow2ScrewX"), "{V}.Tube2Z",
     "{P}.Tube2Angle"),
    ("RJ", ("{V}.JointMidX + {V}.JointScrewX", "{V}.JointMidX - {V}.JointScrewX"),
     "{V}.Tube2Z", "{P}.Tube2Angle"),
)
ELBOW_CLAMP_LABELS = {"E1": "локоть_1", "E2": "локоть_2", "RJ": "тяга"}


def build_elbow_hw(doc, part, vs):
    """Винты и гайки всех трёх хомутов локтя: 1-й трубы, 2-й трубы и тяги.

    Схема та же, что на хомуте шкива: винт сверху через зенковку в
    крышке, гайка в пазу на нижней грани хомута. Головка садится на дно
    зенковки (CapThk - CapWall), гайка — на низ хомута (-ElbowBot).

    Хомут 2 и хомут тяги ПОВЁРНУТЫ на Tube2Angle, а крепёж живёт в
    координатах парта, поэтому положение каждого винта считается
    выражением с поворотом:

        x = PivotX + lx * cos(a) - ly * sin(a)
        y =          lx * sin(a) + ly * cos(a)

    Гайку тоже доворачиваем на Tube2Angle — шестигранник паза повёрнут
    вместе с телом, а у гайки симметрия 60°, так что -90° её не спасают.
    """
    for o in list(doc.Objects):
        if o.Name.startswith("EH_"):
            doc.removeObject(o.Name)
    doc.recompute()

    # длина: от дна зенковки до низа гнезда гайки, чтобы резьба прошла
    # гайку насквозь, но не вышла под хомут (гнездо поднято на ClampNutLift)
    need = (vs.CapThk.Value - vs.CapWall.Value + vs.ElbowBot.Value
            - vs.ClampNutLift.Value)
    length = next((L for L in LIB_SCREW_LENGTHS if L >= need), LIB_SCREW_LENGTHS[-1])
    screw = lib_shape(LIB_SCREWS % length)
    nut = lib_shape(LIB_NUT)
    if screw is None or nut is None:
        print("  крепёж локтя: библиотека деталей недоступна, пропускаю")
        return None, 0

    made = 0
    for tag, xs, zbase, ang in ELBOW_CLAMPS:
        for i, lx in enumerate(xs):
            for sy in ("p", "m"):
                ly = ("" if sy == "p" else "-") + "{V}.ElbowScrewY"
                xe = ("{V}.PivotX + (%s) * cos(%s) - (%s) * sin(%s)"
                      % (lx, ang, ly, ang))
                ye = "(%s) * sin(%s) + (%s) * cos(%s)" % (lx, ang, ly, ang)
                for kind, shape, zexpr, color in (
                        ("Vint", screw,
                         "%s + {V}.CapThk - {V}.CapWall" % zbase,
                         (0.30, 0.32, 0.35)),
                        ("Gayka", nut, "%s - {V}.ElbowBot + {V}.ClampNutLift" % zbase,
                         (0.55, 0.56, 0.58))):
                    o = doc.addObject("Part::Feature",
                                      "EH_%s_%s%d%s" % (kind, tag, i + 1, sy))
                    o.Shape = shape.copy()
                    o.Label = ("Винт_%s_M3x%d_%d%s" % (ELBOW_CLAMP_LABELS[tag],
                                                       length, i + 1, sy)
                               if kind == "Vint" else
                               "Гайка_%s_M3_%d%s" % (ELBOW_CLAMP_LABELS[tag],
                                                     i + 1, sy))
                    part.addObject(o)
                    setx(o, "Placement.Base.x", xe)
                    setx(o, "Placement.Base.y", ye)
                    setx(o, "Placement.Base.z", zexpr)
                    setx(o, "Placement.Rotation.Angle", ang)
                    if App.GuiUp:
                        o.ViewObject.ShapeColor = color
                        o.ViewObject.DiffuseColor = [color]
                    made += 1
    doc.recompute()
    return length, made


def build_motor2(doc):
    """Поставить правый мотор (валом вверх) под венец второго шкива и
    повесить на него ведущий шкив.

    Шкив — App::Link на уже существующий Шкив_ведущий_20T: он
    сделан эскизами с жёстко заданными 20 зубьями, поэтому копировать
    геометрию незачем, достаточно ссылки. Правка оригинала отразится на
    обоих.
    """
    motor = doc.getObject(MOTOR2_NAME)
    drv   = doc.getObject(DRIVER_NAME)
    if motor is None or drv is None:
        print("  моторы: не нашёл %s / %s, пропускаю" % (MOTOR2_NAME, DRIVER_NAME))
        return None
    # левый мотор перевёрнут валом вниз (поворот 180° вокруг X, корпус над
    # фланцем), правый стоит валом ВВЕРХ — корпус под фанерной плитой.
    # Клон правого мотора берёт геометрию левого БЕЗ его Placement, поворот
    # задаётся каждому отдельно. Шкив 2 — ссылка на шкив 1 и ориентацию
    # берёт у него (ступица вверх): на правом моторе он надет ступицей от
    # мотора, винты ступицы — сверху
    flip = App.Rotation(App.Vector(1, 0, 0), 180)
    m1 = doc.getObject("Body")
    for o, zexpr, rot in ((m1, "{V}.Motor1FaceZ + {V}.MotorLen", flip),
                          (motor, "{V}.Motor2FaceZ - {V}.MotorLen", App.Rotation()),
                          (drv, "{V}.Motor1FaceZ - {V}.DrvGap", flip)):
        if o is None:
            continue
        pl = o.Placement
        pl.Rotation = rot
        o.Placement = pl
        setx(o, "Placement.Base.z", zexpr)
    setx(motor, "Placement.Base.x", "{V}.Motor2X")
    setx(motor, "Placement.Base.y", "{V}.Motor2Y")

    link = doc.getObject(DRV2_NAME)
    if link is None:
        link = doc.addObject("App::Link", DRV2_NAME)
        link.LinkedObject = drv
        link.LinkTransform = True      # сохранить собственный Placement оригинала
        parent = [o for o in drv.InList if o.TypeId == "App::Part"]
        if parent:
            parent[0].addObject(link)
    link.Label = DRV2_LABEL
    setx(link, "Placement.Base.x", "{V}.Motor2X")
    setx(link, "Placement.Base.y", "{V}.Motor2Y")
    setx(link, "Placement.Base.z", "{V}.Motor2Lift")
    doc.recompute()
    return link


def build_spacer(doc, part):
    """Труба между подшипниками первого и второго шкива.

    Сидит на валу M8 и упирается ТОЛЬКО во внутренние кольца: снизу в
    подшипник 1 (через отверстие ShaftHoleD в упоре шкива 1), сверху в
    подшипник 2. Вал стягивает всю стопку внутренних колец с проставкой,
    поэтому она неподвижна и ни обо что вращающееся не трётся — оба
    шкива крутятся только на наружных кольцах.
    """
    old = doc.getObject(PROST_NAME)
    if old is not None:
        wipe(doc, old)
        doc.removeObject(old.Name)
        doc.recompute()
    purge_orphans(doc)
    body = doc.addObject("PartDesign::Body", PROST_NAME)
    part.addObject(body)
    body.Label = PROST_LABEL

    add(doc, body, "AdditiveCylinder", "S_Tube",
        {"Radius": "{V}.SpacerOD / 2", "Height": "{V}.SpacerH",
         "Placement.Base.z": "{V}.BrgW"})
    add(doc, body, "SubtractiveCylinder", "S_Bore",
        {"Radius": "{V}.SpacerID / 2", "Height": "{V}.SpacerH + 2 mm",
         "Placement.Base.z": "{V}.BrgW - 1 mm"})
    doc.recompute()
    show_tip(body)
    return body


LIB_SCREWS = ("Mechanical Parts/Fasteners/Bolts & Screws/Metric/"
              "ISO4762_Hex_Socket_Head_Cap_Screw_M3x%d.fcstd")
LIB_SCREW_LENGTHS = (10, 12, 16, 18, 20, 22, 25, 35)   # что есть в библиотеке
LIB_NUT = "Mechanical Parts/Fasteners/Nuts/Metric/ISO4032_Hex_Nut_M3.fcstd"
LIB_BEARING = "Mechanical Parts/Bearings/608ZZ_Ball_Bearing.fcstd"


def lib_shape(rel):
    """Достать геометрию детали из библиотеки и запечь её Placement.

    У Part::Feature свойство Placement и Shape.Placement — одно и то же,
    поэтому собственный разворот библиотечной детали надо внести прямо
    в геометрию, иначе он потеряется при первом же присвоении Placement.
    """
    import os
    path = os.path.join(App.getUserAppDataDir(), "Mod", "parts_library", rel)
    if not os.path.exists(path):
        return None
    d = App.openDocument(path)
    try:
        best = None
        for o in d.Objects:
            sh = getattr(o, "Shape", None)
            if sh is None or sh.isNull() or sh.Volume < 1e-9:
                continue
            best = o.Shape.copy()          # последняя фича цепочки = готовая деталь
        if best is None:
            return None
        m = best.Placement.toMatrix()
        best.Placement = App.Placement()
        return best.transformGeometry(m)
    finally:
        App.closeDocument(d.Name)


def lib_rigid(rel):
    """Достать деталь из библиотеки, сохранив её Placement как есть.

    Отличие от lib_shape: без transformGeometry. Тот пересобирает
    поверхности в B-сплайны, и на 608ZZ это заметно — объём уехал на 1%,
    цилиндрические грани исчезли, а BoundBox стал считаться по
    контрольным точкам и показывал 33x38x7 вместо 22x22x7. Для жёсткого
    поворота пересборка не нужна: Part::Feature наследует Placement
    шейпа вместе с разворотом, остаётся задать только смещение.
    """
    import os
    path = os.path.join(App.getUserAppDataDir(), "Mod", "parts_library", rel)
    if not os.path.exists(path):
        return None
    d = App.openDocument(path)
    try:
        best = None
        for o in d.Objects:
            sh = getattr(o, "Shape", None)
            if sh is None or sh.isNull() or sh.Volume < 1e-9:
                continue
            best = o.Shape.copy()      # последняя фича цепочки = готовая деталь
        return best
    finally:
        App.closeDocument(d.Name)


def build_bearings(doc, part):
    """Подшипники обоих шкивов из библиотеки.

    У первого гнездо открыто вниз, у второго — вверх (снизу ступицу
    занимает рычаг). Разворот осью по Z у библиотечной детали уже зашит
    в Placement шейпа, геометрия центрирована — поэтому задаём только
    смещение на половину толщины.
    """
    for o in list(doc.Objects):
        if o.Name.startswith("BRG_"):
            doc.removeObject(o.Name)
    doc.recompute()
    sh = lib_rigid(LIB_BEARING)
    if sh is None:
        print("  подшипники: библиотека деталей недоступна, пропускаю")
        return 0
    color = (0.62, 0.64, 0.67)
    made = 0
    for name, label, zexpr in (
            ("BRG_1", "Подшипник_608ZZ_1", "{V}.BrgW / 2"),
            ("BRG_2", "Подшипник_608ZZ_2", "{V}.BrgZ2 + {V}.BrgW2 / 2")):
        o = doc.addObject("Part::Feature", name)
        o.Shape = sh.copy()        # Placement с разворотом приходит вместе с ним
        o.Label = label
        part.addObject(o)
        setx(o, "Placement.Base.z", zexpr)
        if App.GuiUp:
            o.ViewObject.ShapeColor = color
            o.ViewObject.DiffuseColor = [color]
        made += 1
    doc.recompute()
    return made


def build_hardware(doc, part, vs):
    """Винты и гайки из библиотеки, расставленные по пазам хомута."""
    for o in list(doc.Objects):
        if o.Name.startswith("HW_"):
            doc.removeObject(o.Name)
    doc.recompute()

    need = (vs.TubeAxisZ.Value + vs.CapThk.Value - vs.CapWall.Value
            - vs.NutZ.Value)
    length = next((L for L in LIB_SCREW_LENGTHS if L >= need), LIB_SCREW_LENGTHS[-1])
    screw = lib_shape(LIB_SCREWS % length)
    nut = lib_shape(LIB_NUT)
    if screw is None or nut is None:
        print("  крепёж: библиотека деталей недоступна, пропускаю")
        return None, 0

    made = 0
    for i, (sx, sy) in enumerate([("ScrewX1", "+"), ("ScrewX1", "-"),
                                  ("ScrewX2", "+"), ("ScrewX2", "-")]):
        ey = ("" if sy == "+" else "-") + "{V}.ScrewY"
        for kind, shape, zexpr, rot, color in (
                ("Vint",  screw, "{V}.TubeAxisZ + {V}.CapThk - {V}.CapWall",
                 None, (0.30, 0.32, 0.35)),
                # доворот гайке не нужен: её грани уже совпадают с пазом.
                # Проверено подбором — габаритная коробка скруглённой детали
                # ориентацию шестигранника не показывает.
                ("Gayka", nut, "{V}.NutZ", None, (0.55, 0.56, 0.58))):
            o = doc.addObject("Part::Feature", "HW_%s%d" % (kind, i + 1))
            o.Shape = shape.copy()
            o.Label = ("Винт_M3x%d_%d" % (length, i + 1) if kind == "Vint"
                       else "Гайка_M3_%d" % (i + 1))
            part.addObject(o)
            if rot is not None:
                pl = o.Placement
                pl.Rotation = rot
                o.Placement = pl
            # хомут крутится с плечом: положение — поворот (x, y) на ShoulderAngle
            setx(o, "Placement.Base.x", "{V}.%s * cos({P}.ShoulderAngle) - (%s) * sin({P}.ShoulderAngle)"
                 % (sx, ey))
            setx(o, "Placement.Base.y", "{V}.%s * sin({P}.ShoulderAngle) + (%s) * cos({P}.ShoulderAngle)"
                 % (sx, ey))
            setx(o, "Placement.Base.z", zexpr)
            setx(o, "Placement.Rotation.Angle", "{P}.ShoulderAngle")
            o.ViewObject.ShapeColor = color
            o.ViewObject.DiffuseColor = [color]
            made += 1
    doc.recompute()
    return length, made


def main():
    doc = pick_doc()
    body = doc.getObject(BODY_NAME)
    part = doc.getObject(PART_NAME)
    print("документ:", doc.Name, "|", doc.FileName)

    ps = ensure_pose(doc)
    vs, created = ensure_varset(doc)
    print("набор переменных '%s' %s" % (vs.Label, "создан" if created else "найден, значения сохранены"))

    build_pulley(doc, body)
    cap = build_cap(doc, part)
    prost = build_spacer(doc, part)
    pul2 = build_pulley2(doc, part)
    screw_len, hw_n = build_hardware(doc, part, vs)
    brg_n = build_bearings(doc, part)
    tube = build_tube(doc)
    elbow, acap, elbow2, bcap, tube2 = build_elbow(doc, doc.getObject(TUBE_PART))
    pv_n, pv_len = build_pivot_hw(doc, doc.getObject(TUBE_PART), vs)
    joint, jcap = build_rod_joint(doc, doc.getObject(TUBE_PART))
    eh_len, eh_n = build_elbow_hw(doc, doc.getObject(TUBE_PART), vs)
    rod, rod_len, rod_n = build_rod(doc, doc.getObject(TUBE_PART), vs)
    drv2 = build_motor2(doc)

    # узел целиком отъезжает от вала левого мотора на межосевое
    # расстояние — вперёд по X и в сторону на пол-шага моторов, так что
    # рука выходит ровно между ними, а моторы остаются ПОЗАДИ неё — и
    # садится по высоте так, чтобы венцы ведущего и ведомого совпали
    setx(part, "Placement.Base.x", "{V}.PulleyAxisX")
    setx(part, "Placement.Base.y", "{V}.ArmAxisY")
    setx(part, "Placement.Base.z", "{V}.BeltPlaneZ - {V}.FlangeThk")
    doc.recompute()

    # ---------------- отчёт ----------------
    sh = body.Shape
    bb = sh.BoundBox
    v = sh.Volume / 1000.0
    cv = cap.Shape.Volume / 1000.0
    print("")
    print("  передача   %d -> %d зубьев, i = %.3f (задано %.3f)"
          % (vs.DriverTeeth, vs.DrivenTeeth, vs.RatioActual, vs.Ratio))
    print("  шкив       делительный Ø%.3f | вершины Ø%.3f | фланец Ø%.3f"
          % (vs.PitchD2, vs.TipD, vs.FlangeD))
    print("  ремень     GT2-%.0f, %.0f мм ширина -> межосевое %.3f мм"
          % (vs.BeltLength, vs.BeltWidth, vs.CenterDist))
    print("             запас длины %+.1f мм (минимум %.1f), зубьев в зацеплении %.1f"
          % (vs.BeltSlack, vs.BeltMin, vs.TeethInMesh))
    if vs.BeltSlack <= 0:
        print("  !! РЕМЕНЬ КОРОТОК для такой передачи — возьмите длиннее "
              "или уменьшите Ratio")
    elif vs.TeethInMesh < 6:
        print("  !! в зацеплении меньше 6 зубьев — ремень будет проскакивать")
    print("  положение  узел на (%.3f, %.3f, %.3f) от вала левого мотора"
          % (part.Placement.Base.x, part.Placement.Base.y,
             part.Placement.Base.z))
    z0 = part.Placement.Base.z + vs.FlangeThk.Value
    print("             венец ведомого z %.3f..%.3f, ведущего %.3f..%.3f"
          % (z0, z0 + vs.RimH.Value,
             vs.BeltPlaneZ.Value, vs.BeltPlaneZ.Value + vs.RimH.Value))
    print("  труба      Ø%.1f, хомут %.0f мм, ось на z=%.1f от низа шкива"
          % (vs.TubeOD, vs.ClampLen, vs.TubeAxisZ))
    print("  окна шкив1 %d шт по %.0f°, R %.1f..%.1f (спица под седлом руки)"
          % (vs.WindowCount, vs.WindowAngle, vs.WindowRin, vs.WindowRout))
    print("  окна шкив2 %d шт по %.0f°, R %.1f..%.1f (спица под рычагом)"
          % (vs.WindowCount2, vs.WindowAngle2, vs.WindowRin2, vs.WindowRout2))
    vint_len = (vs.TubeAxisZ.Value + vs.CapThk.Value - vs.CapWall.Value
                - vs.NutZ.Value)
    print("  винты      шаг %.1f x %.1f мм, нужно не меньше %.1f мм"
          % (vs.ScrewX2 - vs.ScrewX1, 2 * vs.ScrewY, vint_len))
    print("  пазы гаек  %.1f x %.1f, открыты вниз и вбок (гайка заводится сбоку)"
          % (vs.NutAF, vs.NutThk))
    if screw_len:
        print("  крепёж     %d шт из библиотеки: ISO4762 M3x%d + ISO4032 гайка M3"
              % (hw_n, screw_len))
    print("  шкив+седло %.2f x %.2f x %.2f мм | %.1f см3 (PLA ~%.0f г) | тел %d, валидно %s"
          % (bb.XLength, bb.YLength, bb.ZLength, v, v * 1.24, len(sh.Solids), sh.isValid()))
    print("  крышка     %.1f см3 (PLA ~%.0f г) | тел %d, валидно %s"
          % (cv, cv * 1.24, len(cap.Shape.Solids), cap.Shape.isValid()))
    pv = prost.Shape.Volume / 1000.0
    print("  проставка  Ø%.1f/Ø%.1f x %.1f мм (стенка %.1f) | %.1f см3 (PLA ~%.0f г)"
          % (vs.SpacerOD, vs.SpacerID, vs.SpacerH, vs.SpacerWall,
             pv, pv * 1.24))
    print("             зажата между внутренними кольцами подшипников, "
          "z %.1f..%.1f от низа шкива 1" % (vs.BrgW, vs.BrgW.Value + vs.SpacerH.Value))
    p2v = pul2.Shape.Volume / 1000.0
    print("  ступень 2  %d -> %d зубьев, i = %.3f (задано %.3f) | вершины Ø%.3f"
          % (vs.DriverTeeth2, vs.DrivenTeeth2, vs.RatioActual2, vs.Ratio2,
             vs.TipD2))
    print("             ремень GT2-%.0f -> межосевое %.3f мм, запас %+.1f мм, "
          "зубьев в зацеплении %.1f"
          % (vs.BeltLength2, vs.CenterDist2, vs.BeltSlack2, vs.TeethInMesh2))
    if vs.BeltSlack2 <= 0:
        print("  !! РЕМЕНЬ 2 КОРОТОК для этой передачи")
    elif vs.TeethInMesh2 < 6:
        print("  !! у второй ступени в зацеплении меньше 6 зубьев")
    if min(vs.CenterDist.Value, vs.CenterDist2.Value) < vs.ArmAxisY.Value:
        print("  !! межосевое меньше полушага моторов (%.1f) — так их не "
              "расставить, нужен ремень длиннее или меньше MotorGap"
              % vs.ArmAxisY)
    print("  шкив 2     без хомута | %.1f см3 (PLA ~%.0f г)" % (p2v, p2v * 1.24))
    print("             низ фланца z=%.1f, венец z=%.1f..%.1f от низа первого шкива"
          % (vs.Pulley2Z, vs.BeltPlaneZ2, vs.BeltPlaneZ2.Value + vs.RimH.Value))
    print("  подшипники %d шт 608ZZ, оба гнезда открыты вниз: шкив 1 "
          "z 0..%.0f, шкив 2 z %.1f..%.1f"
          % (brg_n, vs.BrgW, vs.BrgZ2.Value, vs.BrgZ2.Value + vs.BrgW.Value))
    print("             упор шкива 1 %.1f мм Ø%.1f, шкива 2 %.1f мм Ø%.1f"
          % (vs.PulleyH.Value - vs.BrgW.Value, vs.ShaftHoleD,
             vs.ShoulderThk2, vs.ShaftHoleD2))
    if vs.ShoulderThk2 <= 0:
        print("  !! у верхнего шкива упор нулевой: BrgW2 >= PulleyH2")
    if abs(vs.BrgOD2.Value - 22.0) > 1e-6 or abs(vs.BrgW2.Value - 7.0) > 1e-6:
        print("  !! BrgOD2/BrgW2 уже не 608ZZ (22x7) — деталь из библиотеки "
              "в гнездо не сядет, меняйте LIB_BEARING")
    print("  рычаг      R%.0f..%.0f до отверстия Ø%.1f, %.0f x %.0f мм, "
          "часть фланца, угол %.0f°"
          % (vs.LeverR0, vs.LeverLen, vs.LeverHoleD, vs.LeverWidth,
             vs.LeverThk, ps.LeverAngle))
    tv = tube.Shape.Volume / 1000.0
    print("  труба      Ø%.1f x %.0f мм, стенка %.1f | отдельный парт «%s» | %.1f см3"
          % (vs.TubeOD, vs.TubeLen, vs.TubeWall, TUBE_PLABEL, tv))
    ev = (elbow.Shape.Volume + acap.Shape.Volume) / 1000.0
    e2v = (elbow2.Shape.Volume + bcap.Shape.Volume) / 1000.0
    t2v = tube2.Shape.Volume / 1000.0
    print("  локоть     ось шарнира на x=%.1f от оси шкива | хомут 1 + крышка "
          "%.1f см3, хомут 2 + крышка %.1f см3"
          % (vs.PivotX, ev, e2v))
    print("             подшипник %d шт 623ZZ Ø%.0f x %.0f, винт M3x%d сверху, "
          "гайка в пазу проушины"
          % (pv_n and 1, vs.PivotBrgOD, vs.PivotBrgW, pv_len))
    print("             хомуты на винтах M3: по 4 шт, гайки в пазах снизу, "
          "нужно не меньше %.1f мм"
          % (vs.CapThk.Value - vs.CapWall.Value + vs.ElbowBot.Value - vs.NutThk.Value))
    print("  труба 2    Ø%.1f x %.0f мм насквозь через хомут 2, угол %.0f° | "
          "вылет %.0f + рабочая %.0f | %.1f см3"
          % (vs.TubeOD, vs.Tube2Full, ps.Tube2Angle,
             vs.LeverLen.Value - vs.JointReach.Value, vs.Tube2Len, t2v))
    jv = (joint.Shape.Volume + jcap.Shape.Volume) / 1000.0
    la = math.radians(ps.LeverAngle.Value - ps.ShoulderAngle.Value)   # в СК руки
    ta = math.radians(ps.Tube2Angle.Value)
    hx = vs.LeverLen.Value * math.cos(la)
    hy = vs.LeverLen.Value * math.sin(la)
    px = vs.PivotX.Value - vs.LeverLen.Value * math.cos(ta)
    py = -vs.LeverLen.Value * math.sin(ta)
    span = math.hypot(px - hx, py - hy)
    print("  шарнир тяги палец на %.0f мм (= LeverLen) от оси локтя, проушина "
          "в полосе z %.1f..%.1f — ровно полоса рычага | хомут %.0f мм + "
          "крышка | %.1f см3"
          % (vs.LeverLen, vs.LeverZ, vs.LeverZ.Value + vs.LeverThk.Value,
             vs.JointGrip, jv))
    print("             труба 2 кончается за %.1f мм до пальца, пролёт "
          "закрывает планка | тяга плоская: Ø%.1f x 2, межцентровое %.2f мм"
          % (vs.JointReach, vs.LeverHoleD, span))
    if vs.LeverZ.Value + vs.LeverThk.Value > vs.Tube2Z.Value + 1e-6:
        print("  !! полоса рычага выше оси трубы 2 — планка проушины полезет в "
              "крышку хомута: уменьшите LeverThk или поднимите трубу 2 "
              "(PivotHeadC)")
    if vs.LeverZ.Value < vs.Tube2Z.Value - vs.ElbowBot.Value - 1e-6:
        print("  !! полоса рычага ниже хомута тяги — планка оторвётся от его "
              "торцевой стенки")
    free = vs.LeverLen.Value - vs.JointReach.Value - vs.ElbowGrip.Value / 2
    if vs.JointGrip.Value + vs.JointWall.Value > free:
        print("  !! хомут тяги (%.0f + стенка %.0f) не влезает между локтем и "
              "пальцем (%.1f мм): уменьшите JointGrip или удлините рычаг"
              % (vs.JointGrip, vs.JointWall, free))
    if vs.JointScrewX.Value <= 0:
        print("  !! JointGrip меньше 12 мм — винтам хомута тяги некуда встать")
    if eh_len:
        print("  крепёж локтя %d шт из библиотеки: ISO4762 M3x%d + гайка M3, "
              "по 4 винта на хомут 1, хомут 2 и хомут тяги"
              % (eh_n, eh_len))
    rv = rod.Shape.Volume / 1000.0
    print("  тяга       межцентровое %.2f мм, планка %.1f x %.1f, глаза R%.1f "
          "под 623ZZ, угол %.1f° | %.1f см3"
          % (ps.RodLen, vs.RodBarW, vs.RodThk, vs.RodEyeR, ps.RodAngle, rv))
    print("             висит на втулках %.1f мм ПОД рычагом и проушиной, z %.1f..%.1f; "
          "параллелограмм замкнут при RodLen == PivotX (%.2f)"
          % (vs.RodStandoff, vs.RodZ, vs.RodZ.Value + vs.RodThk.Value, vs.PivotX))
    if abs(ps.RodLen.Value - vs.PivotX.Value) > 0.01:
        print("  !! тяга (%.2f) не равна плечу (%.2f) — параллелограмм "
              "разомкнут: проверьте LeverAngle и Tube2Angle"
              % (ps.RodLen, vs.PivotX))
    if rod_len:
        print("             шарниры тяги %d деталей: потайной M3x%d заподлицо, "
              "втулка, 623ZZ, шайба, гайка" % (rod_n, rod_len))
    if abs(vs.RodThk.Value - vs.PivotBrgW.Value) > 1e-6:
        print("  !! RodThk (%.1f) не равна ширине 623ZZ (%.1f) — подшипник не "
              "встанет заподлицо" % (vs.RodThk, vs.PivotBrgW))
    print("  моторы     бок о бок ПОЗАДИ руки, шаг %.1f (корпус %.1f + зазор "
          "%.1f), рука выходит между ними"
          % (vs.MotorPitch, vs.MotorSize, vs.MotorGap))
    print("             левый (0, 0, 0), ось шкивов (%.3f, %.3f) — рука "
          "смотрит вдоль +X, от моторов"
          % (vs.PulleyAxisX, vs.ArmAxisY))
    if drv2 is not None:
        print("  мотор 2    (x=%.1f, y=%.1f, z=+%.1f), межосевое %.3f, "
              "ведущий шкив — ссылка на «%s»"
              % (vs.Motor2X, vs.Motor2Y, vs.Motor2Lift, vs.CenterDist2,
                 doc.getObject(DRIVER_NAME).Label))
        if vs.DriverTeeth2 != 20:
            print("  !! DriverTeeth2 = %d, а ведущий шкив в модели — эскизный 20T. "
                  "Расчёт второй ступени и геометрия шкива расходятся"
                  % vs.DriverTeeth2)
    # проставка и втулки вала должны проходить в отверстия упоров шкивов,
    # не касаясь их, и ложиться только на внутренние кольца 608ZZ (Ø12.1)
    if vs.SpacerOD.Value > 12.1 + 1e-6:
        print("  !! проставка Ø%.1f шире внутреннего кольца 608ZZ — заденет "
              "наружное, которое вращается" % vs.SpacerOD)
    if min(vs.ShaftHoleD.Value, vs.ShaftHoleD2.Value) < vs.SpacerOD.Value + 1.0:
        print("  !! отверстие в упоре шкива меньше проставки + 1 мм — проставка "
              "будет тереться о шкив")

    if App.GuiUp:
        import FreeCADGui as Gui
        # активного GUI-документа может не быть (макрос запущен через MCP,
        # пока открывались файлы библиотеки) — вид тогда не трогаем
        gd = Gui.getDocument(doc.Name)
        if gd is not None and gd.activeView() is not None:
            gd.activeView().viewIsometric()
            gd.activeView().fitAll()


if __name__ == "__main__":
    main()
