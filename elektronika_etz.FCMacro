# -*- coding: utf-8 -*-
"""Электроника в ETZ_Robot: плата приводов (STEP из KiCad) с ESP32-S3 и
драйверами в гнёздах, дисплеем, кнопками и индикаторами; под ней на фанере —
аккумулятор, помпа и клапан; рядом — макетная плата 400 (ЕТЗ п. 3.6).

Запускать ПОСЛЕ uzly_etz.FCMacro (основание с удлинением назад — Etz.BaseRear*,
шкивы, плита 2). Детали — Part::Feature с префиксом EL_ в App::Part
«Электроника» (Part_Elec).

Где что стоит и почему:
- Всё — на удлинении фанеры за моторами (x -75..-185, y -25..-205). Туда
  рука не заходит ни в одной позе: плечо — только -110..138°, предплечье
  на парковке и при переезде проходит при y >= -19 (захват на парковке
  висит у (-108, 15)).
- Плата на латунных стойках M3x35 (низ платы z 34): под ней по фанере —
  аккумулятор 3S, помпа и клапан (выше всех помпа, 27).
- Кнопка останова (грибок) и выключатель пока не ставятся — на плате для
  них клеммники X3 (выключатель) и X4 (останов).
- Датчики Холла: плечо — снизу под шкивом 1 на печатной стойке, магнит на
  нижнем фланце шкива 1; предплечье — над шкивом 2 на печатном кронштейне
  с плиты 2, магнит на верхнем фланце шкива 2. Магниты стоят против датчиков
  в позе парковки (плечо 136°, рычаг 56°).
"""
import math, os
import FreeCAD as App
import Part

V = App.Vector
DOC = "ETZ_Robot"
HERE = os.path.dirname(os.path.abspath(__file__)) if "__file__" in dir() else "/home/fedoz/ETZ2067"
STEP = os.path.join(HERE, "elektronika", "etz_plata.step")

PLY = (0.85, 0.70, 0.45)
PRINT = (0.20, 0.45, 0.85)
BRASS = (0.80, 0.62, 0.20)
DARK = (0.12, 0.12, 0.12)
STEEL = (0.75, 0.75, 0.78)

# плата приводов (125 x 110) за моторами: KiCad (u вправо, v вниз) ->
# x = -75 - v (верхний край — к моторам), y = -25 - u
PCB_X0, PCB_Y0 = -75.0, -25.0
BASE_TOP = -1.0                      # уточняется по FR_Base в main()
PCB_STD = 35.0                       # латунные стойки M3x35
PCB_Z = BASE_TOP + PCB_STD           # низ платы
PCB_HOLES = [(4, 4), (121, 4), (4, 106), (121, 106)]
# из расстановки платы (elektronika/gen/layout.py) — для деталей без 3D-модели в KiCad
DRV_AT = [(30.0, 12.0), (56.0, 12.0)]        # A1, A2 (поворот 270)
SB_AT = [(40.0, 40.0), (40.0, 52.0), (40.0, 64.0)]   # кнопки 6x6, вывод 1
DISPLAY_UV = (11.0, 36.0, 37.0, 69.0)        # проекция модуля 0,96" ST7735S
ESP_UV = (0.5, 63.85, 80.25, 105.6)          # ESP32-S3-DevKitC-1, USB к u = 0
VAC_AT = (40.0, 76.0)                        # гнездо модуля датчика вакуума (выв. 1)
# Холл
HALL_R = 25.7
PARK_SHOULDER, PARK_LEVER = 136.0, 56.0


def box(x0, x1, y0, y1, z0, z1):
    return Part.makeBox(x1 - x0, y1 - y0, z1 - z0, V(x0, y0, z0))


def cyl(r, z0, z1, x=0.0, y=0.0):
    return Part.makeCylinder(r, z1 - z0, V(x, y, z0))


def cyl_y(r, y0, y1, x, z):
    return Part.makeCylinder(r, y1 - y0, V(x, y0, z), V(0, 1, 0))


def D():
    return App.getDocument(DOC)


def container(doc, name, label, parent=None):
    o = doc.getObject(name)
    if o is None:
        o = doc.addObject("App::Part", name)
        if parent is not None:
            parent.addObject(o)
    o.Label = label
    return o


def feat(doc, parent, name, label, shape, color=None):
    o = doc.getObject(name)
    if o is None:
        o = doc.addObject("Part::Feature", name)
        parent.addObject(o)
    o.Label = label
    o.Shape = shape
    if color is not None and App.GuiUp:
        o.ViewObject.ShapeColor = tuple(float(c) for c in color)
    return o


def purge(doc):
    for o in list(doc.Objects):
        if o.Name.startswith("EL_"):
            doc.removeObject(o.Name)


def global_pl(o):
    pl = App.Placement()
    g = o.getParentGeoFeatureGroup()
    while g is not None:
        pl = g.Placement.multiply(pl)
        g = g.getParentGeoFeatureGroup()
    return pl


# ---------------------------------------------------------------- плата из KiCad
def load_board():
    """STEP платы -> (форма в координатах робота, цвета граней или None)."""
    shapes, colors = [], []
    if App.GuiUp:
        import ImportGui
        tmp = App.newDocument("EL_tmp")
        try:
            ImportGui.insert(STEP, tmp.Name)
            tmp.recompute()
            for o in tmp.Objects:
                if not hasattr(o, "Shape") or o.TypeId == "App::Part" or o.Shape.isNull():
                    continue
                if o.InList and any(p.TypeId == "Part::Feature" for p in o.InList):
                    continue
                if not o.Shape.Faces:
                    continue
                s = Part.getShape(o, "", needSubElement=False, refine=False, transform=True)
                pl = global_pl(o)
                s = s.copy()
                s.Placement = pl.multiply(s.Placement)
                dc = list(o.ViewObject.DiffuseColor) if hasattr(o.ViewObject, "DiffuseColor") else []
                if len(dc) != len(s.Faces):
                    c = o.ViewObject.ShapeColor
                    dc = [c] * len(s.Faces)
                # только тела: в STEP есть и отдельные грани (медь, шелкография) —
                # у части из них бесконечный габарит
                col = {f.hashCode(): c for f, c in zip(s.Faces, dc)}
                for so in s.Solids:
                    shapes.append(so)
                    colors += [col.get(f.hashCode(), dc[0]) for f in so.Faces]
        finally:
            App.closeDocument(tmp.Name)
    else:
        shapes = Part.read(STEP).Solids
    comp = Part.makeCompound(shapes)
    # подложка: самое большое тело толщиной ~1.6
    sols = [s for s in comp.Solids if 1.4 < s.BoundBox.ZLength < 1.8 and s.BoundBox.XLength > 100]
    sub = max(sols, key=lambda s: s.BoundBox.XLength * s.BoundBox.YLength)
    bb = sub.BoundBox
    # KiCad STEP: X = u + X0, Y = -v + Y0  ->  робот: x = PCB_X0 - v, y = PCB_Y0 - u
    comp.rotate(V(0, 0, 0), V(0, 0, 1), -90)
    # после поворота: x = Y, y = -X; совмещаем край u=0 (X = bb.XMin) и v=0 (Y = bb.YMax)
    dz = PCB_Z - bb.ZMin
    comp.translate(V(PCB_X0 - bb.YMax, PCB_Y0 + bb.XMin, dz))
    return comp, (colors if colors and len(colors) == len(comp.Faces) else None)


def uv(u, v, z=0.0):
    return V(PCB_X0 - v, PCB_Y0 - u, z)


def rect(u0, u1, v0, v1, z0, z1):
    a, b = uv(u0, v0), uv(u1, v1)
    x0, x1 = sorted((a.x, b.x)); y0, y1 = sorted((a.y, b.y))
    return box(x0, x1, y0, y1, z0, z1)


def board_extras(doc, P):
    """Чего нет в библиотеке 3D KiCad: модули в гнёздах (TMC2209, ESP32-S3,
    дисплей, датчик вакуума) и кнопки 6x6."""
    ztop = PCB_Z + 1.6
    for k, (fu, fv) in enumerate(DRV_AT):
        # место модуля повёрнуто на 270: модуль u fu-19.05..fu+1.27, v fv-1.25..fv+13.95
        u0, u1, v0, v1 = fu - 19.05, fu + 1.27, fv - 1.25, fv + 13.95
        z0 = ztop + 8.5                       # гнёзда PBS 8.5 мм
        m = rect(u0, u1, v0, v1, z0, z0 + 1.6)
        c = uv((u0 + u1) / 2, (v0 + v1) / 2)
        m = m.fuse(box(c.x - 4.5, c.x + 4.5, c.y - 4.5, c.y + 4.5, z0 + 1.6, z0 + 6.6))   # радиатор
        feat(doc, P, "EL_Drv%d" % (k + 1), "Модуль_TMC2209_%d" % (k + 1), m, (0.55, 0.05, 0.05))
    # ESP32-S3-DevKitC-1: плата 62.7 x 25.4 на штырях над гнёздами, модуль
    # WROOM у вывода 1 (дальний от USB конец), два USB-C у края платы
    u0, u1, v0, v1 = ESP_UV
    ze = ztop + 11.0
    esp = rect(u0, u1, v0, v1, ze, ze + 1.6)
    esp = esp.fuse(rect(u1 - 19.5, u1 - 1.5, v0 + 0.5, v1 - 0.5, ze + 1.6, ze + 4.8))
    for vc in (v0 + 6.0, v1 - 6.0):
        esp = esp.fuse(rect(u0 - 0.5, u0 + 7.0, vc - 4.5, vc + 4.5, ze + 1.6, ze + 4.8))
    feat(doc, P, "EL_Esp", "ESP32-S3-DevKitC-1", esp, (0.08, 0.08, 0.10))
    # дисплей 0,96" 80x160 на гнезде PBS-8 (8.5) + штыри с пластиком 2.5
    u0, u1, v0, v1 = DISPLAY_UV
    zd = ztop + 11.0
    feat(doc, P, "EL_DispPcb", "Дисплей_0.96_ST7735S_плата", rect(u0 + 0.5, u1 - 0.5, v0 + 1.0, v1 - 1.0, zd, zd + 1.6),
         (0.10, 0.25, 0.55))
    feat(doc, P, "EL_DispLcd", "Дисплей_0.96_ST7735S_экран", rect(u0 + 2.0, u1 - 2.0, v0 + 6.0, v1 - 3.0, zd + 1.6, zd + 3.2),
         (0.05, 0.05, 0.05))
    # модуль датчика вакуума XGZP6847A стоит в гнезде PBS-3 вертикально
    vu, vv = VAC_AT
    vs = rect(vu - 3.0, vu + 15.0, vv - 0.8, vv + 0.8, ztop + 8.5, ztop + 26.5)
    c = uv(vu + 6.0, vv - 0.8 - 3.5)
    vs = vs.fuse(rect(vu + 1.0, vu + 11.0, vv - 6.8, vv - 0.8, ztop + 14.5, ztop + 24.5))
    vs = vs.fuse(Part.makeCylinder(1.5, 6.0, V(c.x, c.y, ztop + 24.5)))
    feat(doc, P, "EL_VacSensor", "Датчик_вакуума_XGZP6847A_модуль", vs, (0.10, 0.35, 0.15))
    for k, (bu, bv) in enumerate(SB_AT):
        cu, cv = bu + 3.25, bv + 2.25
        b_ = rect(cu - 3.0, cu + 3.0, cv - 3.0, cv + 3.0, ztop, ztop + 3.5)
        c = uv(cu, cv)
        feat(doc, P, "EL_SB%d" % (k + 1), "Кнопка_6x6_SB%d" % (k + 1),
             b_.fuse(cyl(1.75, ztop + 3.5, ztop + 8.5, c.x, c.y)), DARK)


def standoffs(doc, P, base_top):
    for i, (u, v) in enumerate(PCB_HOLES):
        c = uv(u, v)
        s = cyl(2.75, base_top, PCB_Z, c.x, c.y).cut(cyl(1.25, base_top - 1, PCB_Z + 1, c.x, c.y))
        feat(doc, P, "EL_PcbStd%d" % (i + 1), "Стойка_латунь_M3x35_ВВ_плата_%d" % (i + 1), s, BRASS)
        h = cyl(2.75, PCB_Z + 1.6, PCB_Z + 1.6 + 1.65, c.x, c.y)
        feat(doc, P, "EL_PcbScr%d" % (i + 1), "Винт_платы_M3x6_ISO7380_%d" % (i + 1), h, DARK)


# ---------------------------------------------------------------- под платой и рядом
def under(doc, P, base_top):
    z = base_top
    # аккумулятор 3S (3x18650 в держателе), банки вдоль y
    x0, y0 = -170.0, -113.0
    hol = box(x0, x0 + 58.0, y0, y0 + 78.0, z, z + 21.0)
    hol = hol.cut(box(x0 + 1.5, x0 + 56.5, y0 + 1.5, y0 + 76.5, z + 2.0, z + 22.0))
    feat(doc, P, "EL_BatHolder", "Аккумулятор_3S_держатель", hol, DARK)
    cells = [Part.makeCylinder(9.25, 72.0, V(x0 + 9.75 + 19.25 * k, y0 + 3.0, z + 11.25), V(0, 1, 0))
             for k in range(3)]
    feat(doc, P, "EL_BatCells", "Аккумулятор_3S_18650x3", cells[0].fuse(cells[1:]), (0.15, 0.35, 0.80))
    # вакуумная помпа 6 В: мотор Ø24 x 32 + головка 27 x 27 x 27, лёжа вдоль y
    px, pz = -91.5, z + 13.5
    pump = cyl_y(12.0, -100.0, -68.0, px, pz).fuse(box(px - 13.5, px + 13.5, -68.0, -41.0, z, z + 27.0))
    for dx in (-5.0, 5.0):
        pump = pump.fuse(cyl_y(2.0, -41.0, -35.0, px + dx, z + 20.0))
    feat(doc, P, "EL_Pump", "Помпа_вакуумная_6В", pump, DARK)
    # клапан сброса 6 В, нормально открытый
    vl = box(-106.0, -76.0, -125.0, -112.0, z, z + 13.0).fuse(cyl(6.0, z + 13.0, z + 26.0, -91.0, -118.5))
    feat(doc, P, "EL_Valve", "Клапан_6В_НО", vl, (0.30, 0.30, 0.32))
    # макетная плата 400 точек (ЕТЗ п. 3.6) — рядом с разъёмами А, Б, В
    # (правый край платы, y -150)
    feat(doc, P, "EL_Breadboard", "Макетная_плата_400_точек",
         box(-185.0 + 1.0, -185.0 + 83.5, -205.0 + 1.0, -205.0 + 55.5, z, z + 8.5), (0.95, 0.95, 0.93))


# ---------------------------------------------------------------- датчики Холла
def hall(doc, P):
    d = doc
    part2 = d.getObject("Part002")
    ax, ay, az = part2.Placement.Base.x, part2.Placement.Base.y, part2.Placement.Base.z
    # плечо: датчик снизу под шкивом 1 на оси +X от вала
    hx, hy = ax + HALL_R, ay
    post = box(hx - 4.0, hx + 4.0, hy - 5.0, hy + 5.0, -1.0, az - 5.0)
    feat(d, P, "EL_HallPost1", "Стойка_датчика_Холла_плеча_печать", post, PRINT)
    to92 = lambda x, y, z0: box(x - 2.25, x + 2.25, y - 2.0, y + 2.0, z0, z0 + 2.5)
    feat(d, P, "EL_Hall1", "Датчик_Холла_A3144_плечо", to92(hx, hy, az - 5.0), DARK)
    # магниты 3x1 — в Part002, поворачиваются вместе со своими шкивами
    phi = math.radians(-PARK_SHOULDER)           # в парковке над датчиком (угол 0)
    m1 = cyl(1.5, -1.0, 0.0, HALL_R * math.cos(phi), HALL_R * math.sin(phi))
    o = feat(d, part2, "EL_MagS", "Магнит_3x1_шкив_1", m1, STEEL)
    o.setExpression(".Placement.Rotation.Angle", "Poza.ShoulderAngle")
    # предплечье: датчик над шкивом 2 со стороны моторов (угол 180)
    sh2 = d.getObject("Body_Pulley2").Shape
    z2 = sh2.BoundBox.ZMax                       # верх шкива 2 в координатах Part002
    phi2 = math.radians(180.0 - PARK_LEVER)
    m2 = cyl(1.5, z2, z2 + 1.0, HALL_R * math.cos(phi2), HALL_R * math.sin(phi2))
    o = feat(d, part2, "EL_MagL", "Магнит_3x1_шкив_2", m2, STEEL)
    o.setExpression(".Placement.Rotation.Angle", "Poza.LeverAngle")
    gz = az + z2                                  # верх шкива 2 в глобальных
    sx, sy = ax - HALL_R, ay
    feat(d, P, "EL_Hall2", "Датчик_Холла_A3144_предплечье", to92(sx, sy, gz + 2.0), DARK)
    pb = d.getObject("FR_PlateB")
    pbb = pb.Shape.BoundBox if pb.getParentGeoFeatureGroup() is None else None
    if pbb is None:
        s = pb.Shape.copy()
        s.Placement = global_pl(pb).multiply(s.Placement)
        pbb = s.BoundBox
    # кронштейн: лапа на плите 2 у её правого края, стойка, полка над шкивом 2
    fx1 = pbb.XMax - 1.0
    foot = box(fx1 - 10.0, fx1, sy + 6.0, sy + 16.0, pbb.ZMax, pbb.ZMax + 3.0)
    riser = box(fx1 - 6.0, fx1, sy + 6.0, sy + 16.0, pbb.ZMax, gz + 7.5)
    arm = box(fx1 - 6.0, sx + 4.0, sy - 4.0, sy + 16.0, gz + 4.5, gz + 7.5)
    feat(d, P, "EL_HallBr2", "Кронштейн_датчика_Холла_предплечья_печать", foot.fuse([riser, arm]), PRINT)


def main():
    global PCB_Z
    doc = D()
    purge(doc)
    P = container(doc, "Part_Elec", "Электроника")
    base = doc.getObject("FR_Base")
    bs = base.Shape.copy()
    bs.Placement = global_pl(base).multiply(bs.Placement)
    base_top = float(bs.BoundBox.ZMax)
    if abs(base_top) > 1e3:
        # в только что открытом документе габарит копии бывает бесконечным —
        # верх фанеры: пол полигона + 6 мм
        base_top = doc.getObject("Etz").FloorZ.Value + 6.0
    e = doc.getObject("Etz")
    if not hasattr(e, "BaseRearX0") or e.BaseRearX0.Value > -180:
        print("!! основание без удлинения назад (Etz.BaseRear*): сначала uzly_etz.FCMacro")
    PCB_Z = base_top + PCB_STD
    comp, colors = load_board()
    App.setActiveDocument(doc.Name)
    o = feat(doc, P, "EL_Board", "Плата_приводов_ETZ_v3", comp, (0.10, 0.40, 0.15))
    if colors and App.GuiUp:
        try:
            o.ViewObject.DiffuseColor = colors
        except Exception:
            pass
    board_extras(doc, P)
    standoffs(doc, P, base_top)
    under(doc, P, base_top)
    hall(doc, P)
    doc.recompute()
    print("Электроника: %d деталей" % len([x for x in doc.Objects if x.Name.startswith("EL_")]))


if __name__ in ("__main__", "elek"):
    main()
