# -*- coding: utf-8 -*-
# proverka_etz.FCMacro
#
# Проверка устройства на соответствие ЕТЗ 2026-27 и на собираемость.
# Ничего в документе не меняет (кроме временной высоты магнита Etz.MagnetZ,
# которая возвращается назад).
#
#   static()   — пересечения всех деталей в текущей позе (все пары)
#   sweep()    — пересечения подвижных звеньев со всем остальным по сетке
#                углов суставов, покрывающей рабочую зону, и в позах над
#                каждой клеткой (с захватом внизу)
#   tz()       — требования ЕТЗ: зоны, досягаемость клеток с допусками
#                листа, ход Z над стопками, парковка, скорость
#   bearings() — все вращательные пары и на чём они вращаются
#   screws()   — доступ ключа к каждому винту с учётом порядка сборки
#   nuts()     — гайки: не проворачиваются в гнезде и заводятся по пазу;
#                открытые гайки — есть место под рожковый ключ
#   mass()     — масса и запас устойчивости от опрокидывания
#   run_all()  — всё подряд, итог в конце
#
# Каждая функция возвращает список замечаний; пустой список — всё в порядке.

import math

import FreeCAD as App
import Part

V = App.Vector
DOCN = "ETZ_Robot"
TOL = 0.05          # мм3: объём пересечения меньше — считаем касанием


def D():
    return App.getDocument(DOCN)


# ---------------------------------------------------------------------------
# Сбор деталей в глобальных координатах
# ---------------------------------------------------------------------------
def global_shape(o):
    sh = Part.getShape(o, "", needSubElement=False, refine=False, transform=True)
    pl = App.Placement()
    g = o.getParentGeoFeatureGroup()
    while g is not None:
        pl = g.Placement.multiply(pl)
        g = g.getParentGeoFeatureGroup()
    sh = sh.copy()
    sh.Placement = pl.multiply(sh.Placement)
    return sh


def parts():
    """Все детали устройства: тела PartDesign, Part::Feature вне тел, ссылки."""
    doc = D()
    out = {}
    for o in doc.Objects:
        if o.Name.startswith("PG_"):
            continue
        if o.TypeId == "PartDesign::Body":
            pass
        elif o.TypeId == "App::Link":
            pass
        elif o.TypeId == "Part::Feature":
            if any(p.TypeId == "PartDesign::Body" for p in o.InList):
                continue
        else:
            continue
        try:
            sh = global_shape(o)
        except Exception:
            continue
        if sh.isNull() or sh.Volume < 1e-3:
            continue
        out[o.Name] = sh
    return out


def label(n):
    o = D().getObject(n)
    return "%s (%s)" % (o.Label, n) if o is not None else n


# ---------------------------------------------------------------------------
# Что с чем пересекаться ВПРАВЕ (по конструкции)
# ---------------------------------------------------------------------------
# резьба в моторе не смоделирована — винты моторов входят в корпус;
# вал мотора сидит в ступице ведущего шкива; ремень лежит на зубьях;
# шлиц серво — в шестерне; зубья в зацеплении — по проверке зацепления.
ALLOWED = [
    ("FR_MotScrA", "Body"), ("FR_MotScrB", "Body001"),
    ("Body", "Pulley"), ("Body001", "Driver2"),
    ("FR_Belt1", "Pulley"), ("FR_Belt1", "Body003"),
    ("FR_Belt2", "Driver2"), ("FR_Belt2", "Body_Pulley2"),
    ("EF_ServoZ", "EF_GearZ"), ("CR_ServoR", "CR_GearRt"),
    ("EF_GearZ", "CR_Carriage"), ("CR_GearSp", "CR_GearRt"),
    # саморезы SG90 нарезают резьбу в пластике сами
    ("EF_SvScrZ", "EF_Bracket"), ("CR_SvScr", "CR_Carriage"),
    ("CAM_SvScr", "CAM_Head"), ("CAM_BoardScr", "CAM_Bracket"),
    ("CAM_Servo", "CAM_GearSv"),
    # резьба латунных стоек не смоделирована (отверстие Ø2.5 под метчик)
    ("FR_PlScr", "FR_Std"), ("FR_BaseScr", "FR_Std"),
]


_ALLOWED_MEMO = {}


def allowed(a, b):
    k = (a, b)
    r = _ALLOWED_MEMO.get(k)
    if r is None:
        r = _ALLOWED_MEMO[k] = _ALLOWED_MEMO[(b, a)] = _allowed(a, b)
    return r


def _allowed(a, b):
    for p, q in ALLOWED:
        if (a.startswith(p) and b.startswith(q)) or (a.startswith(q) and b.startswith(p)):
            # "Body" не должен ловить Body_*: точное совпадение для коротких имён
            if (p in ("Body", "Body001") and p not in (a, b)) or \
               (q in ("Body", "Body001") and q not in (a, b)):
                continue
            return True
    return False


def box_hit(A, B, gap=0.0):
    """Пересекаются ли габариты (BoundBox) с зазором gap."""
    return not (A.XMax + gap < B.XMin or B.XMax + gap < A.XMin or
                A.YMax + gap < B.YMin or B.YMax + gap < A.YMin or
                A.ZMax + gap < B.ZMin or B.ZMax + gap < A.ZMin)


def bb_hit(a, b, gap=0.0):
    return box_hit(a.BoundBox, b.BoundBox, gap)


def box_dist(A, B):
    """Расстояние между габаритами — нижняя граница расстояния между телами."""
    dx = max(A.XMin - B.XMax, B.XMin - A.XMax, 0.0)
    dy = max(A.YMin - B.YMax, B.YMin - A.YMax, 0.0)
    dz = max(A.ZMin - B.ZMax, B.ZMin - A.ZMax, 0.0)
    return math.sqrt(dx * dx + dy * dy + dz * dz)


def overlap(a, b):
    if not bb_hit(a, b):
        return 0.0
    try:
        return a.common(b).Volume
    except Exception:
        return -1.0


# Тела вращения вокруг оси шкивов: их пересечение с тем, что вращается
# вокруг этой же оси (плечо, рычаг), от угла не зависит — считаем один раз.
AXISYM = ("BRG_1", "BRG_2", "FR_ShaftBolt", "FR_ShaftBushLo", "FR_ShaftBushHi", "Body_Prost")
_AXI_MEMO = {}


def _axi_key(na, nb):
    for x, y in ((na, nb), (nb, na)):
        if x in AXISYM and group_of(y) in ("shoulder", "lever"):
            return (x, y)
    return None


def bboxes(d):
    """Габариты всех деталей словаря — один раз, а не на каждую пару:
    BoundBox у формы не кэшируется и на ~6000 парах позы стоил секунды."""
    return {n: s.BoundBox for n, s in d.items()}


def collide(sa, sb, skip_allowed=True, ba=None, bb=None):
    """Пары с пересечением объёмом > TOL между словарями sa и sb.
    ba, bb — готовые габариты (bboxes), если уже посчитаны."""
    ba = ba if ba is not None else bboxes(sa)
    bb = bb if bb is not None else (ba if sb is sa else bboxes(sb))
    bad = []
    for na, a in sa.items():
        A = ba[na]
        for nb, b in sb.items():
            if na >= nb and sa is sb:
                continue
            if na == nb:
                continue
            if not box_hit(A, bb[nb]):
                continue
            if skip_allowed and allowed(na, nb):
                continue
            ak = _axi_key(na, nb)
            if ak is not None and ak in _AXI_MEMO:
                v = _AXI_MEMO[ak]
            else:
                try:
                    v = a.common(b).Volume
                except Exception:
                    v = -1.0
                if ak is not None:
                    _AXI_MEMO[ak] = v
            if v > TOL or v < 0:
                bad.append((na, nb, v))
    return bad


# ---------------------------------------------------------------------------
# Кинематика
# ---------------------------------------------------------------------------
# (точные имена тел, префиксы деталей)
GROUPS = {
    "shoulder": ({"Body003", "Body_Cap", "Body_Tube", "Body_Elbow", "Body_ElbowCap", "EL_MagS"},
                 ("HW_", "PV_", "EH_Vint_E1", "EH_Gayka_E1")),
    "lever": ({"Body_Pulley2", "EL_MagL"}, ("RD_VintA", "RD_VtulA", "RD_BrgA", "RD_ShaybaA", "RD_GaykaA")),
    "forearm": ({"Body_Elbow2", "Body_Elbow2Cap", "Body_Tube2", "Body_RodJoint", "Body_RodJointCap"},
                ("EH_Vint_E2", "EH_Gayka_E2", "EH_Vint_RJ", "EH_Gayka_RJ", "RD_VintB", "RD_VtulB",
                 "RD_BrgB", "RD_ShaybaB", "RD_GaykaB", "EF_", "CR_")),
    "rod": ({"Body_Rod"}, ()),
}


_GROUP_MEMO = {}


def group_of(n):
    r = _GROUP_MEMO.get(n)
    if r is None:
        r = "static"
        for g, (exact, pref) in GROUPS.items():
            if n in exact or n.startswith(pref):
                r = g
                break
        _GROUP_MEMO[n] = r
    return r


def SPINDLE_AXIS(holder):
    """x оси шпинделя во фрейме предплечья: центр держателя присосок без
    штуцера трубки (он торчит вбок и сдвигает центр габарита)."""
    import Part as _P
    sol = max(holder.Shape.Solids, key=lambda s_: s_.Volume)
    cyl_faces = [f for f in sol.Faces if f.Surface.__class__.__name__ == "Cylinder"
                 and abs(f.Surface.Axis.z) > 0.99]
    big = max(cyl_faces, key=lambda f: f.Surface.Radius)
    return big.Surface.Center.x


def geom():
    d = D().getObject("Drive")
    S = V(d.PulleyAxisX.Value, d.ArmAxisY.Value, 0)
    L1 = d.PivotX.Value
    lev = d.LeverLen.Value
    # вылет захвата — ось магнита в фрейме предплечья (от оси локтя)
    grip = D().getObject("CR_CupHolder") or D().getObject("CR_Magnet")   # присоски / прежний магнит
    Le = grip.Shape.BoundBox.Center.x if grip.Name == "CR_Magnet" else SPINDLE_AXIS(grip)
    # поза документа — VarSet Poza (углы плеча и рычага абсолютные, предплечья —
    # от плеча); в старых документах углы жили в Drive и плечо было на 0
    ps = D().getObject("Poza") or d
    t1_0 = ps.ShoulderAngle.Value if hasattr(ps, "ShoulderAngle") else 0.0
    return dict(S=S, L1=L1, lev=lev, t1_0=t1_0, t2_0=t1_0 + ps.Tube2Angle.Value, lv_0=ps.LeverAngle.Value,
                Le=Le)


def rz_pl(c, ang, move=None):
    """Поворот вокруг вертикали через c на ang (град), затем сдвиг move."""
    pl = App.Placement(V(0, 0, 0), App.Rotation(V(0, 0, 1), ang), V(c.x, c.y, 0))
    if move is not None:
        pl = App.Placement(move, App.Rotation()).multiply(pl)
    return pl


def moved(shape, pl):
    """Форма в другом положении без копирования геометрии: transformed(copy=False)
    в ~100 раз быстрее copy() + rotate() и даёт ту же форму."""
    if pl.isIdentity():
        return shape
    return shape.transformed(pl.toMatrix(), copy=False)


def rz(shape, c, ang):
    return moved(shape, rz_pl(c, ang))


def pose(base, g, t1, t2):
    """Детали в позе (t1 — угол плеча, t2 — абсолютный угол предплечья, град)."""
    S = g["S"]
    P0 = S + V(g["L1"] * math.cos(math.radians(g["t1_0"])), g["L1"] * math.sin(math.radians(g["t1_0"])), 0)
    P1 = S + V(g["L1"] * math.cos(math.radians(t1)), g["L1"] * math.sin(math.radians(t1)), 0)
    A0 = S + V(g["lev"] * math.cos(math.radians(g["lv_0"])), g["lev"] * math.sin(math.radians(g["lv_0"])), 0)
    lv = t2 + 180.0
    A1 = S + V(g["lev"] * math.cos(math.radians(lv)), g["lev"] * math.sin(math.radians(lv)), 0)
    pls = {"static": App.Placement(),
           "shoulder": rz_pl(S, t1 - g["t1_0"]),
           "lever": rz_pl(S, t2 - g["t2_0"]),
           "forearm": rz_pl(P0, t2 - g["t2_0"], P1 - P0),
           "rod": rz_pl(A0, t1 - g["t1_0"], A1 - A0)}
    return {n: moved(sh, pls[group_of(n)]) for n, sh in base.items()}


def ik(g, x, y, sign=1):
    """Глобальная точка захвата (x, y) -> (t1, t2) или None."""
    S = g["S"]
    dx, dy = x - S.x, y - S.y
    r = math.hypot(dx, dy)
    L1, Le = g["L1"], g["Le"]
    c = (r * r - L1 * L1 - Le * Le) / (2 * L1 * Le)
    if abs(c) > 1:
        return None
    q2 = sign * math.acos(c)
    t1 = math.atan2(dy, dx) - math.atan2(Le * math.sin(q2), L1 + Le * math.cos(q2))
    return math.degrees(t1), math.degrees(t1 + q2)


def set_cam(a):
    """Угол консоли камеры (Etz.CamAngle); возвращает прежний."""
    e = D().getObject("Etz")
    if not hasattr(e, "CamAngle"):
        return None
    if a is None:
        return None
    old = e.CamAngle.Value
    e.CamAngle = a
    D().recompute()
    return old


def set_magnet(z):
    e = D().getObject("Etz")
    old = e.MagnetZ.Value
    e.MagnetZ = z
    D().recompute()
    return old


# ---------------------------------------------------------------------------
# Полигон
# ---------------------------------------------------------------------------
def poly_xy(p):
    """Глобальная точка робота -> координаты полигона."""
    d, e = D().getObject("Drive"), D().getObject("Etz")
    return (p.x - d.PulleyAxisX.Value + e.PolyShaftX.Value,
            p.y - d.ArmAxisY.Value + e.PolyShaftY.Value)


def robot_xy(px, py):
    d, e = D().getObject("Drive"), D().getObject("Etz")
    return V(px - e.PolyShaftX.Value + d.PulleyAxisX.Value,
             py - e.PolyShaftY.Value + d.ArmAxisY.Value, 0)


def cells(dx=0.0, dy=0.0, rot=0.0):
    """Центры клеток и отбоя (полигон), лист сдвинут на dx,dy и повёрнут на rot."""
    O = (563.0, 126.5)
    c = (475.0, 250.0)          # центр листа А4
    out = []
    pts = []
    for k, row in enumerate("АБВГДЕ"):
        for n in range(9):
            pts.append(("%s%d" % (row, n), O[0] - 28.0 * (k + 1), O[1] + 28.0 * n))
    for k in range(1, 6):
        pts.append(("Отбой%d" % k, O[0] - 28.0 * k, O[1] + 252.0))
    a = math.radians(rot)
    for nm, x, y in pts:
        xr = c[0] + (x - c[0]) * math.cos(a) - (y - c[1]) * math.sin(a) + dx
        yr = c[1] + (x - c[0]) * math.sin(a) + (y - c[1]) * math.cos(a) + dy
        out.append((nm, xr, yr))
    return out


def zone_forbidden(fz, h=400.0):
    """Объём над полигоном, где устройство НЕ может быть до/после работы:
    всё, кроме зон 1 и 2 (область поля, зазоры и вне полигона)."""
    o = robot_xy(0, 0)
    big = Part.makeBox(2000, 2000, h, V(o.x - 700, o.y - 700, fz - 1))
    ok = [Part.makeBox(350, 500, h + 2, V(o.x, o.y, fz - 2)),
          Part.makeBox(250, 80, h + 2, V(o.x + 350, o.y, fz - 2)),
          Part.makeBox(250, 80, h + 2, V(o.x + 350, o.y + 420, fz - 2))]
    return big.cut(ok)


def zone_forbidden_boxes(fz, h=400.0):
    """То же, что zone_forbidden, но набором из 5 непересекающихся коробок:
    слева, справа, спереди, сзади от полигона и область поля между полосами
    зоны 2. Габарит каждой — сама коробка, поэтому лишних булевых нет
    (у цельной области габарит накрывает всё устройство)."""
    o = robot_xy(0, 0)
    z0 = fz - 1
    mk = lambda x0, x1, y0, y1: Part.makeBox(x1 - x0, y1 - y0, h, V(o.x + x0, o.y + y0, z0))
    return [mk(-700, 0, -700, 1300), mk(600, 1300, -700, 1300),
            mk(0, 600, -700, 0), mk(0, 600, 500, 1300), mk(350, 600, 80, 420)]


def forb_volume(shapes, boxes, stop=None):
    """Объём деталей в запретной области; stop — прервать, как только больше."""
    vol = 0.0
    bxs = [b.BoundBox for b in boxes]
    for s in shapes:
        sb = s.BoundBox
        for b, B in zip(boxes, bxs):
            if box_hit(sb, B):
                vol += s.common(b).Volume
                if stop is not None and vol > stop:
                    return vol
    return vol


def forb_dist(shapes, boxes):
    """Точное наименьшее расстояние от деталей до запретной области. Пары
    перебираются по возрастанию расстояния габаритов (нижней границы), и
    перебор кончается, когда граница не меньше уже найденного."""
    bxs = [b.BoundBox for b in boxes]
    cand = sorted((box_dist(s.BoundBox, B), i, j) for i, s in enumerate(shapes)
                  for j, B in enumerate(bxs))
    best = 1e9
    for lb, i, j in cand:
        if lb >= best:
            break
        best = min(best, shapes[i].distToShape(boxes[j])[0])
    return best


# ---------------------------------------------------------------------------
# Проверки
# ---------------------------------------------------------------------------
def static(report=True):
    issues = []
    for mz in (38.6, 4.0):
        old = set_magnet(mz)
        P = parts()
        bad = collide(P, P)
        set_magnet(old)
        for a, b, v in bad:
            issues.append("пересечение (магнит +%.1f): %s <-> %s, %.2f мм3" % (mz, label(a), label(b), v))
    if report:
        print("STATIC: деталей %d, замечаний %d" % (len(P), len(issues)))
        for i in issues:
            print("  ", i)
    return issues


# от каких углов зависит взаимное положение пары групп: пару, уже
# проверенную при тех же значениях, второй раз не считаем
PAIR_KEY = {
    ("shoulder", "static"): ("t1",), ("lever", "static"): ("t2",),
    ("forearm", "static"): ("t1", "t2"), ("rod", "static"): ("t1", "t2"),
    ("lever", "shoulder"): ("q2",), ("forearm", "shoulder"): ("q2",),
    ("rod", "shoulder"): ("q2",), ("forearm", "lever"): ("t1", "t2"),
    ("lever", "rod"): ("q2",), ("forearm", "rod"): ("q2",),
}


def _cross(Pp, groups_moving, angles=None, cache=None):
    """Пересечения между разными группами (внутри группы — проверено static)."""
    by = {}
    for n, s in Pp.items():
        by.setdefault(group_of(n), {})[n] = s
    bxs = {gr: bboxes(d) for gr, d in by.items()}
    bad = []
    names = sorted(by.keys())
    for i in range(len(names)):
        for j in range(i + 1, len(names)):
            ga, gb = names[i], names[j]
            if ga not in groups_moving and gb not in groups_moving:
                continue
            if angles is not None and cache is not None:
                deps = PAIR_KEY.get((ga, gb)) or PAIR_KEY.get((gb, ga))
                if deps:
                    key = (ga, gb) + tuple(round(angles[k], 3) for k in deps)
                    if key in cache:
                        continue
                    cache.add(key)
            bad += collide(by[ga], by[gb], ba=bxs[ga], bb=bxs[gb])
    return bad


# Рабочая зона захвата: перед зоной 1 — над полем, зоной 2 и по пути к
# парковке (x полигона >= WORK_X0). Позы сетки, где захват левее или
# далеко за полигоном, программе не нужны и не проверяются: туда рука
# не должна ходить (например, при t1 = -110 и почти прямом локте тяга
# проходит над левым мотором).
WORK_X0 = 340.0
WORK_Y = (15.0, 485.0)       # центр захвата не за краем полигона


def eff_poly(g, t1, q2):
    S = g["S"]
    x = S.x + g["L1"] * math.cos(math.radians(t1)) + g["Le"] * math.cos(math.radians(t1 + q2))
    y = S.y + g["L1"] * math.sin(math.radians(t1)) + g["Le"] * math.sin(math.radians(t1 + q2))
    return poly_xy(V(x, y, 0))


def in_work(g, t1, q2):
    px, py = eff_poly(g, t1, q2)
    return px >= WORK_X0 and WORK_Y[0] <= py <= WORK_Y[1]


def sweep(t1_rng=(-110, 10, 10), q2_rng=(56, 156, 8), report=True):
    """Сетка (t1, q2): плечо и относительный угол локтя, захват поднят.
    Проверяются позы, где захват в рабочей зоне (in_work)."""
    g = geom()
    old = set_magnet(38.6)
    base = parts()
    issues = []
    seen = set()
    cache = set()
    n = 0
    skipped = 0
    t1 = t1_rng[0]
    while t1 <= t1_rng[1] + 1e-9:
        q2 = q2_rng[0]
        while q2 <= q2_rng[1] + 1e-9:
            if not in_work(g, t1, q2):
                skipped += 1
                q2 += q2_rng[2]
                continue
            Pp = pose(base, g, t1, t1 + q2)
            for a, b, v in _cross(Pp, ("shoulder", "lever", "forearm", "rod"),
                                  dict(t1=t1, t2=t1 + q2, q2=q2), cache):
                key = (a, b)
                if key not in seen:
                    seen.add(key)
                    issues.append("поза t1=%+.0f q2=%.0f: %s <-> %s, %.1f мм3"
                                  % (t1, q2, label(a), label(b), v))
            n += 1
            q2 += q2_rng[2]
        t1 += t1_rng[2]
    set_magnet(old)
    if report:
        print("SWEEP: поз %d (ещё %d вне рабочей зоны захвата, x полигона < %.0f), t1 %s, q2 %s; "
              "замечаний %d" % (n, skipped, WORK_X0, t1_rng[:2], q2_rng[:2], len(issues)))
        for i in issues:
            print("  ", i)
    return issues


def sweep_cells(report=True):
    """Захват опущен на шашку (магнит +5) над каждой клеткой: ничего,
    кроме магнита, не ниже верха стопки из 5 шашек в соседних клетках,
    и устройство не задевает себя и станину."""
    g = geom()
    e = D().getObject("Etz")
    fz = e.FloorZ.Value
    old = set_magnet(5.0)
    base = parts()
    low_ok = ("CR_Magnet", "CR_Cup", "CR_HolderNut", "CR_Ext", "CR_Screw")
    issues = []
    worst = 1e9
    worst_n = None
    for nm, px, py in cells():
        p = robot_xy(px, py)
        sol = ik(g, p.x, p.y)
        if sol is None:
            issues.append("клетка %s недостижима" % nm)
            continue
        Pp = pose(base, g, *sol)
        for a, b, v in _cross(Pp, ("shoulder", "lever", "forearm", "rod")):
            issues.append("клетка %s: %s <-> %s, %.1f мм3" % (nm, label(a), label(b), v))
        # всё подвижное, что оказалось над областью поля (x полигона > 350),
        # кроме магнита и его удлинителя, должно идти выше стопки из 5 шашек
        for n_, s in Pp.items():
            if group_of(n_) == "static" or n_.startswith(low_ok):
                continue
            if poly_xy(V(s.BoundBox.XMax, 0, 0))[0] <= 350.0:
                continue
            h = s.BoundBox.ZMin - (fz + 25.0)
            if h < worst:
                worst, worst_n = h, (n_, nm)
    set_magnet(old)
    if worst < 2.0:
        issues.append("при захвате с поля %s (клетка %s) всего на %.1f мм выше стопки из 5 шашек"
                      % (label(worst_n[0]), worst_n[1], worst))
    if report:
        print("CELLS: над каждой клеткой с магнитом на шашке; ниже всех над полем — %s (клетка %s), "
              "запас над стопкой 5 шт: %.1f мм; замечаний %d"
              % (label(worst_n[0]) if worst_n else "-", worst_n[1] if worst_n else "-", worst, len(issues)))
        for i in issues:
            print("  ", i)
    return issues


def tz(report=True):
    doc = D()
    d, e = doc.getObject("Drive"), doc.getObject("Etz")
    g = geom()
    fz = e.FloorZ.Value
    issues = []
    lines = []
    P = parts()

    # 1. опора: только основание касается поля, и оно целиком в зоне 1
    base = P["FR_Base"]
    bb = base.BoundBox
    x0, y0 = poly_xy(V(bb.XMin, bb.YMin, 0))
    x1, y1 = poly_xy(V(bb.XMax, bb.YMax, 0))
    lines.append("основание на полигоне: x %.1f..%.1f, y %.1f..%.1f (зона 1: x 0..350, y 0..500)"
                 % (x0, x1, y0, y1))
    if x0 < 0 or x1 > 350 or y0 < 0 or y1 > 500:
        issues.append("основание выходит за зону 1")
    if x1 > 347:
        issues.append("основание ближе 3 мм к границе зоны 1 (допуск зон ±3 мм)")
    low = [n for n, s in P.items() if s.BoundBox.ZMin < fz + 0.5 and n != "FR_Base"]
    if low:
        issues.append("кроме основания до поля достают: %s" % ", ".join(low))
    if abs(bb.ZMin - fz) > 1e-6:
        issues.append("основание не стоит на поле (z %.2f, поле %.2f)" % (bb.ZMin, fz))

    # 2. парковка: всё устройство над зонами 1 и 2 (до старта и после финиша).
    #    Ищем позу перебором; берём ту, что с наибольшим запасом до запретной
    #    области. Её же печатаем — это поза, в которую программа паркует руку.
    forb = zone_forbidden_boxes(fz)
    old = set_magnet(38.6)
    base_p = parts()
    set_magnet(old)
    moving = {n: s for n, s in base_p.items() if group_of(n) != "static"}
    static_out = [n for n, s in base_p.items() if group_of(n) == "static"
                  and forb_volume([s], forb) > TOL]
    if static_out:
        issues.append("неподвижные детали над запретной областью: %s" % ", ".join(static_out))
    best = None
    t1, q2 = PARK                  # поза парковки; подробно — в park()
    Pp = pose(moving, g, t1, t1 + q2)
    if forb_volume(list(Pp.values()), forb, stop=TOL) <= TOL:
        best = (forb_dist(list(Pp.values()), forb), t1, q2)
    if best is None:
        issues.append("в позе парковки PARK устройство выходит за зоны 1-2")
    else:
        park = (best[1], best[1] + best[2])
        Pp = pose(base_p, g, *park)
        bad = _cross(Pp, ("shoulder", "lever", "forearm", "rod"))
        for a, b, v in bad:
            issues.append("парковка: %s <-> %s" % (label(a), label(b)))
        lines.append("парковка: t1=%.0f°, q2=%.0f° — всё над зонами 1-2, запас до границы %.1f мм"
                     % (best[1], best[2], best[0]))
        if best[0] < 3.0:
            issues.append("в позе парковки запас до границы зон меньше допуска 3 мм")

    # 3. досягаемость клеток с допусками листа: сдвиг 5 мм, поворот 3°
    qs, t1s = [], []
    for dx in (-5, 0, 5):
        for dy in (-5, 0, 5):
            for rot in (-3, 0, 3):
                for nm, px, py in cells(dx, dy, rot):
                    p = robot_xy(px, py)
                    sol = ik(g, p.x, p.y)
                    if sol is None:
                        issues.append("недостижима клетка %s (лист %+d,%+d,%+d°)" % (nm, dx, dy, rot))
                        continue
                    t1s.append(sol[0])
                    qs.append(sol[1] - sol[0])
    lines.append("все 59 позиций (54 клетки + 5 отбоя) с допусками листа: t1 %.0f..%.0f°, угол в локте "
                 "q2 %.0f..%.0f° (сингулярности параллелограмма — 0 и 180)"
                 % (min(t1s), max(t1s), min(qs), max(qs)))
    if min(qs) < 25 or max(qs) > 160:
        issues.append("рабочая зона подходит к сингулярности параллелограмма ближе 20°")

    # 4. вертикаль: ход магнита и высоты стопок
    import importlib
    zs = math.pi * 1.0 * 22 / 2.0
    zmin, zmax = 4.0, 4.0 + zs
    lines.append("магнит: от поля +%.1f до +%.1f мм (ход %.1f за 180° SG90)" % (zmin, zmax, zs))
    if zmin > 5.0:
        issues.append("магнит не опускается до шашки на поле (+5)")
    if zmax - 5.0 < 25.0 + 3.0:
        issues.append("с шашкой в захвате не пройти над стопкой из 5 шашек с запасом 3 мм")
    else:
        lines.append("  шашка в захвате проходит над стопкой из 5 шт с запасом %.1f мм" % (zmax - 5.0 - 25.0))
    lines.append("  берёт верхнюю шашку стопки 1..5 (магнит +5..+25), ставит на стопку до 4 шт")

    # 5. поворот шашки 0..360 (11 кл., ЗЭ)
    lines.append("поворот захвата: SG90 0..180° через z13 -> z26 = 0..360°")

    # 6. скорость: шаговик 1 об/с (консервативно), передача 4
    w = 2 * math.pi * 1.0 / d.RatioActual
    rmax = g["L1"] + g["Le"]
    lines.append("скорость: при 1 об/с мотора угловая %.2f рад/с, захват до %.0f мм/с (ТЗ: >= 100)"
                 % (w, w * 150.0))
    if w * 150.0 < 100:
        issues.append("скорость манипулятора < 100 мм/с при 1 об/с мотора")

    # 7. касаться поля может только захват: при работе ниже стопки только магнит
    if report:
        print("TZ:")
        for l in lines:
            print("  ", l)
        print("   замечаний %d" % len(issues))
        for i in issues:
            print("   !!", i)
    return issues


# Поза парковки — в ней робот ставят на полигон до старта и в неё же
# программа возвращает руку после финиша (п. 3.1 ЕТЗ, 10-11 кл.).
PARK = (136.0, 100.0)          # t1 (плечо), q2 (угол в локте), град: рука сложена
                               # позади-слева от оси, захват — за фанерой над полигоном.
                               # Прежняя поза (-100, 90) держала узел над полосой
                               # зоны 2 (80 мм на узел ~70) — запас 5 мм, при
                               # ошибке 2° узел выходил за полигон
PARK_T1_FROM = 10.0            # переезд: из рабочей зоны (t1 <= 10, sweep) при q2 = PARK
PARK_TOL = 2.0                 # погрешность шаговиков/руки при выставлении, град
ZONE_TOL = 3.0                 # допуск размеров зон полигона


def park(report=True):
    """До начала и после окончания работы: проекция устройства только в
    зонах 1 и 2, опора только на зону 1, в позе парковки ничто ни с чем
    не пересекается. Поза PARK ± PARK_TOL, магнит вверху и внизу."""
    e = D().getObject("Etz")
    g = geom()
    fz = e.FloorZ.Value
    forb = zone_forbidden_boxes(fz)
    names = ("слева от полигона (x < 0)", "справа от полигона (x > 600)",
             "снизу от полигона (y < 0)", "сверху от полигона (y > 500)",
             "операционное поле (x 350..600, y 80..420)")
    # дополнительно: целиком ли над зоной 1 (за x 350 — уже зона 2)
    o = robot_xy(0, 0)
    z1x = Part.makeBox(1000, 2000, 400.0, V(o.x + 350.0, o.y - 700.0, fz - 1))
    issues, lines = [], []
    worst = {}
    t1p, q2p = PARK
    oc = set_cam(e.CamStow.Value)          # до старта и после финиша консоль сложена
    for mz in (38.6, 4.0):
        old = set_magnet(mz)
        P = parts()
        set_magnet(old)
        # опора: до поля достаёт только фанера, и она — в зоне 1
        low = [n for n, s_ in P.items() if s_.BoundBox.ZMin < fz + 0.5 and n != "FR_Base"]
        if low:
            issues.append("магнит +%.1f: кроме основания до поля достают %s" % (mz, ", ".join(low)))
        for dt in (-PARK_TOL, 0.0, PARK_TOL):
            for dq in (-PARK_TOL, 0.0, PARK_TOL):
                t1, q2 = t1p + dt, q2p + dq
                Pp = pose(P, g, t1, t1 + q2)
                shapes = list(Pp.items())
                for k, (bx, nm) in enumerate(zip(forb, names)):
                    v = forb_volume([s_ for _, s_ in shapes], [bx], stop=TOL)
                    if v > TOL:
                        issues.append("t1=%.0f q2=%.0f магнит +%.1f: детали над «%s»" % (t1, q2, mz, nm))
                        continue
                    B = bx.BoundBox
                    cand = sorted((box_dist(s_.BoundBox, B), n) for n, s_ in shapes)
                    best = (1e9, None)
                    for lb, n in cand:
                        if lb >= best[0]:
                            break
                        dd = Pp[n].distToShape(bx)[0]
                        if dd < best[0]:
                            best = (dd, n)
                    if nm not in worst or best[0] < worst[nm][0]:
                        worst[nm] = (best[0], best[1], t1, q2, mz)
                mv = [s_ for n, s_ in shapes if group_of(n) != "static"]
                if forb_volume(mv, [z1x], stop=TOL) <= TOL:
                    d1 = forb_dist(mv, [z1x])
                    if "z1" not in worst or d1 < worst["z1"][0]:
                        worst["z1"] = (d1, t1, q2)
                else:
                    worst["z1"] = (-1.0, t1, q2)
                bad = _cross(Pp, ("shoulder", "lever", "forearm", "rod"))
                if bad:
                    for a, b, v in bad:
                        issues.append("парковка t1=%.0f q2=%.0f, магнит +%.1f: %s <-> %s"
                                      % (t1, q2, mz, label(a), label(b)))
        # переезд из рабочей зоны: q2 = PARK, плечо от PARK_T1_FROM до PARK шагом 2°
        # (при q2 ± PARK_TOL); во время работы выходить за полигон можно, нельзя
        # только задевать
        if mz == 38.6:
            npath = 0
            t = PARK_T1_FROM
            while t <= t1p + PARK_TOL + 1e-6:
                for dq in (-PARK_TOL, 0.0, PARK_TOL):
                    npath += 1
                    Pp = pose(P, g, t, t + q2p + dq)
                    for a, b, v in _cross(Pp, ("shoulder", "lever", "forearm", "rod")):
                        issues.append("переезд на парковку t1=%.0f q2=%.0f: %s <-> %s"
                                      % (t, q2p + dq, label(a), label(b)))
                t += 2.0
            lines.append("переезд из рабочей зоны: q2 = %.0f°, плечо %.0f -> %.0f°, поз %d"
                         % (q2p, PARK_T1_FROM, t1p + PARK_TOL, npath))
    # габарит проекции в координатах полигона (по коробкам — с запасом)
    old = set_magnet(38.6)
    Pp = pose(parts(), g, t1p, t1p + q2p)
    set_magnet(old)
    set_cam(oc)
    xs, ys = [], []
    for s_ in Pp.values():
        bb = s_.BoundBox
        for x_, y_ in ((bb.XMin, bb.YMin), (bb.XMax, bb.YMax)):
            px, py = poly_xy(V(x_, y_, 0))
            xs.append(px)
            ys.append(py)
    lines.append("поза парковки t1=%.0f°, q2=%.0f° (±%.0f°), магнит вверху и внизу"
                 % (t1p, q2p, PARK_TOL))
    lines.append("габарит проекции на полигоне: x %.1f..%.1f, y %.1f..%.1f" % (min(xs), max(xs), min(ys), max(ys)))
    if "z1" in worst:
        if worst["z1"][0] < 0:
            lines.append("  подвижные части выходят за зону 1 (над зоной 2) при t1=%.0f q2=%.0f — по ЕТЗ можно"
                         % worst["z1"][1:])
        else:
            lines.append("  всё устройство над ЗОНОЙ 1, запас подвижных частей до x 350: %.1f мм (t1=%.0f, q2=%.0f)"
                         % worst["z1"])
    for nm in names:
        if nm in worst:
            dd, n, t1, q2, mz = worst[nm]
            lines.append("  до «%s»: %.1f мм — %s (t1=%.0f, q2=%.0f)" % (nm, dd, label(n), t1, q2))
            if dd < ZONE_TOL:
                issues.append("до «%s» меньше допуска зон %.0f мм: %.1f" % (nm, ZONE_TOL, dd))
    if report:
        print("PARK (начало и конец работы):")
        for l in lines:
            print("  ", l)
        print("   замечаний %d" % len(issues))
        for i in issues:
            print("   !!", i)
    return issues


CAM_FOV = (60.0, 47.0)          # IMX179 AF: по длинной стороне кадра (вдоль Y полигона), по короткой
CAM_FOV_MARGIN = 2.0            # град — запас у края кадра
MAST_EXTRA = 150.0              # мачта может торчать выше головы: проверка на столько


def cam(report=True):
    """Камера на откидной консоли: в работе (CamWork) объектив над листом и
    видит весь лист с допусками (сдвиг 5 мм, поворот 3°) и стопки до 5;
    вид на клетки и метки не загорожен рукой в позе парковки; консоль
    поворачивается из сложенного положения в рабочее без касаний; в работе
    всё подвижное руки ниже камеры."""
    doc = D()
    e = doc.getObject("Etz")
    issues, lines = [], []
    if not hasattr(e, "CamAngle"):
        return ["нет камеры (Etz.CamAngle)"]
    g = geom()
    fz = e.FloorZ.Value
    stow, work = e.CamStow.Value, e.CamWork.Value
    oc = set_cam(work)
    old = set_magnet(38.6)
    P = parts()
    set_magnet(old)
    lens = P["CAM_Lens"].BoundBox
    Lc = V((lens.XMin + lens.XMax) / 2.0, (lens.YMin + lens.YMax) / 2.0, lens.ZMin)
    h = Lc.z - fz
    lp = poly_xy(Lc)
    lines.append("объектив над полем %.0f мм, над точкой полигона (%.1f, %.1f) — центр листа (475, 250)"
                 % (h, lp[0], lp[1]))
    # 1. поле зрения: углы листа с допусками, на поле и на высоте стопки из 5
    worst = 1e9
    c = (475.0, 250.0)
    for dx in (-5, 5):
        for dy in (-5, 5):
            for rot in (-3, 3):
                a = math.radians(rot)
                for sx in (-1, 1):
                    for sy in (-1, 1):
                        x, y = sx * 105.0, sy * 148.5
                        px = c[0] + x * math.cos(a) - y * math.sin(a) + dx
                        py = c[1] + x * math.sin(a) + y * math.cos(a) + dy
                        q = robot_xy(px, py)
                        for zz in (0.0, 25.0):
                            dz = h - zz
                            ay = math.degrees(math.atan2(abs(q.y - Lc.y), dz))
                            ax = math.degrees(math.atan2(abs(q.x - Lc.x), dz))
                            worst = min(worst, CAM_FOV[0] / 2.0 - ay, CAM_FOV[1] / 2.0 - ax)
    lines.append("поле зрения %g x %g°: весь лист (сдвиг ±5, поворот ±3°, и на поле, и на стопке из 5) "
                 "в кадре, запас до края кадра %.1f°" % (CAM_FOV[0], CAM_FOV[1], worst))
    if worst < CAM_FOV_MARGIN:
        issues.append("лист с допусками не помещается в кадр (запас %.1f° < %.1f°)" % (worst, CAM_FOV_MARGIN))
    # 2. разрешение: мм на пиксель в центре и на краю (3264 px по длинной стороне)
    span = 2 * h * math.tan(math.radians(CAM_FOV[0] / 2.0))
    lines.append("кадр на поле %.0f x %.0f мм; 8 Мп: %.1f пикс/мм — модуль QR 21x21 на 15 мм = %.1f пикс"
                 % (span, 2 * h * math.tan(math.radians(CAM_FOV[1] / 2.0)), 3264.0 / span,
                    3264.0 / span * 15.0 / 21.0))
    # 3. не загорожено: рука в позе парковки, лучи на центры клеток и метки
    Pp = pose(P, g, PARK[0], PARK[0] + PARK[1])
    targets = [(nm, px, py) for nm, px, py in cells()]
    targets += [("ArUco27", 563.0, 126.5), ("ArUco28", 563.0, 350.5), ("ArUco29", 395.0, 378.5)]
    blocked = []
    for nm, px, py in targets:
        q = robot_xy(px, py)
        for zz in (5.0, 25.0):
            seg = Part.makeLine(V(Lc.x, Lc.y, Lc.z - 0.1), V(q.x, q.y, fz + zz))
            sb = seg.BoundBox
            for n, s_ in Pp.items():
                if n in ("CAM_Lens",):
                    continue
                if not box_hit(s_.BoundBox, sb):
                    continue
                if s_.distToShape(seg)[0] < 1e-6:
                    blocked.append("%s(+%g): %s" % (nm, zz, n))
                    break
    lines.append("лучи на %d клеток/меток (верх шашки и стопки из 5): загорожено %d"
                 % (len(targets), len(blocked)))
    if blocked:
        issues.append("вид загорожен: " + ", ".join(blocked[:8]))
    # 4. в работе всё подвижное руки ниже камеры (высоты от позы не зависят)
    cam_low = min(s_.BoundBox.ZMin for n, s_ in P.items() if n.startswith(("CAM_Lens", "CAM_Board",
                                                                         "CAM_Bracket", "CAM_Boom",
                                                                         "CAM_Hub", "CAM_Br")))
    arm_hi = max(s_.BoundBox.ZMax for n, s_ in P.items() if group_of(n) != "static")
    lines.append("консоль с камерой от z %.0f, рука до z %.0f: зазор %.0f мм в любой позе"
                 % (cam_low, arm_hi, cam_low - arm_hi))
    if cam_low - arm_hi < 10.0:
        issues.append("консоль камеры ближе 10 мм к руке по высоте")
    # 5. поворот консоли stow -> work без касаний (шаг 4°), гнутся только поворотные детали.
    #    Голова на мачте ставится на любую высоту, поэтому мачта может торчать
    #    выше неё — проверяем и с мачтой, продлённой на MAST_EXTRA вверх
    boom = [o.Name for o in doc.getObject("Part_CamBoom").Group]
    mb = P["CAM_Mast"].BoundBox
    mast_x = Part.makeCylinder(mb.XLength / 2.0, MAST_EXTRA,
                               V((mb.XMin + mb.XMax) / 2.0, (mb.YMin + mb.YMax) / 2.0, mb.ZMax))
    mast_gap = 1e9
    n_ok = 0
    a = stow
    while True:
        set_cam(a)
        Q = parts()
        mv = {n: s_ for n, s_ in Q.items() if n in boom}
        rest = {n: s_ for n, s_ in Q.items() if n not in boom}
        rest["мачта +%g мм" % MAST_EXTRA] = mast_x
        for n, s_ in mv.items():
            if box_hit(s_.BoundBox, mast_x.BoundBox, 30.0):
                mast_gap = min(mast_gap, s_.distToShape(mast_x)[0])
        for x, y, v in collide(mv, rest):
            issues.append("поворот консоли %.0f°: %s <-> %s" % (a, label(x), label(y)))
        n_ok += 1
        if a <= work + 1e-6:
            break
        a = max(work, a - 4.0)
    lines.append("консоль: сложена %.1f° -> в работе %.1f° (поворот %.1f°, SG90 %.0f° через z13 -> z26), "
                 "проверено положений %d" % (stow, work, stow - work, (stow - work) * 26.0 / 13.0, n_ok))
    if (stow - work) * 26.0 / 13.0 > 175.0:
        issues.append("SG90 консоли: нужно %.0f° — больше 175°" % ((stow - work) * 26.0 / 13.0))
    lines.append("мачта, продлённая на %g мм выше головы: до поворотных деталей не ближе %.1f мм"
                 % (MAST_EXTRA, mast_gap))
    if mast_gap < 3.0:
        issues.append("мачта выше головы ближе 3 мм к консоли (%.1f мм)" % mast_gap)
    set_cam(oc)
    if report:
        print("CAM:")
        for l in lines:
            print("  ", l)
        print("   замечаний %d" % len(issues))
        for i in issues:
            print("   !!", i)
    return issues


def bearings(report=True):
    """Таблица вращательных пар — по построению модели."""
    doc = D()
    d = doc.getObject("Drive")
    rows = [
        ("плечо (шкив 1 на валу)", "608ZZ x1 (BRG_1)", "вал M8 неподвижен, внутренние кольца зажаты стопкой"),
        ("шкив 2 / рычаг на валу", "608ZZ x1 (BRG_2)", "то же"),
        ("локоть", "623ZZ (PV_Brg)", "наружное кольцо в хомуте 2, внутреннее под винтом"),
        ("тяга — рычаг (A)", "623ZZ (RD_BrgA)", "в глазу тяги; втулка+шайба по внутр. кольцу"),
        ("тяга — шарнир тяги (B)", "623ZZ (RD_BrgB)", "то же"),
        ("шпиндель захвата", "625ZZ x2 (CR_Brg1/2)", "стопка внутр. колец стянута винтом M5 в гайку держателя"),
        ("каретка Z", "MGN9H на рельсе MGN9", "покупная шариковая линейная направляющая"),
        ("консоль камеры", "625ZZ x2 (CAM_Brg1/2)", "ось M5 неподвижна, сбоку от мачты; внутр. кольца "
                                                     "на буртике головы"),
    ]
    issues = []
    # вращающиеся детали касаются только наружных колец: размеры
    if d.SpacerOD.Value > 12.1 + 1e-6:
        issues.append("проставка шире внутреннего кольца 608ZZ")
    if min(d.ShaftHoleD.Value, d.ShaftHoleD2.Value) < d.SpacerOD.Value + 1.0:
        issues.append("упор шкива ближе 0.5 мм к проставке/втулке")
    for n in ("BRG_1", "BRG_2", "PV_Brg", "RD_BrgA", "RD_BrgB", "CR_Brg1", "CR_Brg2",
              "CAM_Brg1", "CAM_Brg2"):
        if doc.getObject(n) is None:
            issues.append("нет подшипника %s" % n)
    if report:
        print("BEARINGS:")
        for r in rows:
            print("   %-26s %-26s %s" % r)
        for i in issues:
            print("   !!", i)
    return issues


# порядок сборки: шаг -> префиксы. Ключ проверяется против деталей
# с шагом <= шага винта (собранных к этому моменту).
STEPS = [
    (20, ("FR_PlateA", "Body", "FR_MotScrA")),            # мотор 1 к плите на столе
    (21, ("FR_PlateB", "Body001", "FR_MotScrB")),            # мотор 2 под плитой, винты сверху
    (30, ("Pulley", "Driver2")),
    (33, ("FR_Base", "FR_Std", "FR_Column", "FR_BaseIns", "FR_BaseScr",
          "FR_ShaftBolt")),             # стойки на фанеру снизу; болт вала — головкой в колонну
    (40, ("FR_PlScrA",)),                                 # плита 1 на латунные стойки
    (41, ("FR_PlScrB",)),
    (50, ("FR_ShaftBushLo", "Body003", "BRG_1", "FR_Belt1", "Body_Tube", "Body_Cap", "HW_")),
    (60, ("Body_Elbow", "Body_ElbowCap", "EH_Vint_E1", "EH_Gayka_E1")),
    (61, ("PV_Brg", "Body_Elbow2", "PV_Nut", "PV_Screw")),
    (62, ("Body_Tube2", "Body_Elbow2Cap", "EH_Vint_E2", "EH_Gayka_E2")),
    (63, ("Body_RodJoint", "Body_RodJointCap", "EH_Vint_RJ", "EH_Gayka_RJ")),
    (64, ("EF_Bracket", "EF_BracketCap", "EF_ClNut", "EF_ClScr", "EF_Insert", "EF_Rail",
          "EF_RailScr")),
    (65, ("EF_ServoZ", "EF_SvScrZ")),
    (66, ("CR_Block",)),                                  # каретка MGN9H на рельсе
    (70, ("CR_Carriage", "CR_Brg", "CR_InnerSp", "CR_Ext", "CR_Magnet", "CR_Cup", "CR_HolderNut",
          "CR_GearSp", "CR_Screw",
          "CR_ServoR", "CR_SvScr")),
    (71, ("CR_GearRt",)),
    (72, ("CR_BlkScr",)),                                 # плита каретки к MGN9H спереди
    (75, ("EF_GearZ",)),
    (80, ("Body_Prost", "Body_Pulley2", "BRG_2", "FR_Belt2", "FR_ShaftBushHi", "FR_ShaftWash",
          "FR_ShaftNut")),
    (90, ("Body_Rod", "RD_")),
    # камера: пробка на конец болта вала, мачта на пробку
    (93, ("CAM_Plug", "CAM_PlugNutM8", "CAM_Mast", "CAM_PlugScr", "CAM_PlugNut")),
    # голова надевается на мачту и зажимается на нужной высоте
    (94, ("CAM_Head", "CAM_HeadScr", "CAM_HeadNut", "CAM_AxNut", "CAM_Servo", "CAM_SvScr")),
    # ступица: гайки хомута в пазы, 625ZZ, ось M5 — ключом сверху через
    # открытое гнездо, пока консоли нет
    (95, ("CAM_Hub", "CAM_HubNut", "CAM_Brg", "CAM_SpIn", "CAM_SpTop", "CAM_AxBolt")),
    (96, ("CAM_Boom", "CAM_HubCap", "CAM_HubScr")),
    (97, ("CAM_Bracket", "CAM_BrScr", "CAM_BrNut", "CAM_Board", "CAM_Lens", "CAM_BoardScr")),
    (98, ("CAM_GearSv",)),                                # шестерня на шлиц — консоль сложена
]


def step_of(n):
    best = None
    for st, pref in STEPS:
        for p in pref:
            if n == p or (n.startswith(p) and p not in ("Body", "Body001", "Body_Elbow", "Body_Tube",
                                                        "Pulley")):
                if best is None or len(p) > best[1]:
                    best = (st, len(p))
    return best[0] if best else 999


# винты: (префикс, R ключа, R головки, головка заходит снаружи по оси).
# Ключи: M3 — шестигранник 2.5 (R1.5 по углам), M4 — 3, M5 — 4, M8 — 6;
# саморезы SG90 — крестовая отвёртка Ø3. Винт шарнира локтя ставится
# головкой в карман хомута 2 СНИЗУ, до запрессовки подшипника, — для него
# проверяется только проход ключа через технологическое отверстие.
SCREWS = [
    ("FR_MotScrB", 1.2, 2.85, True), ("FR_PlScr", 1.2, 2.85, True),   # ISO 7380, ключ 2
    ("FR_MotScr", 1.5, 2.75, True),
    ("FR_BaseScr", 1.5, 3.1, True),
    ("HW_Vint", 1.5, 2.75, True), ("EH_Vint", 1.5, 2.75, True),
    ("PV_Screw", 1.5, 2.75, False), ("RD_Vint", 1.1, 3.4, True),
    ("EF_ClScr", 1.5, 2.75, True), ("CR_Screw", 2.3, 4.25, True),
    ("EF_SvScrZ", 1.5, 2.0, True), ("CR_SvScr", 1.5, 2.0, True),
    ("EF_RailScr", 1.5, 2.75, True), ("CR_BlkScr", 1.5, 2.75, True),
    ("CAM_PlugScr", 1.5, 2.75, True),
    ("CAM_HeadScr", 1.5, 2.75, True), ("CAM_AxBolt", 2.3, 4.25, True),
    ("CAM_HubScr", 1.5, 2.75, True), ("CAM_BrScr", 1.5, 2.75, True),
    ("CAM_SvScr", 1.5, 2.0, True), ("CAM_BoardScr", 1.5, 1.9, True),
]


def _screw_axis(sh):
    """Ось винта (наружу, в сторону ключа) и точка торца головки, глобально.
    sh — форма винта ИЗ ТОГО ЖЕ набора, что и остальные детали (одна поза)."""
    # у всех винтов ось — локальная Z фигуры, головка — в +Z
    pl = sh.Placement
    ax = pl.Rotation.multVec(V(0, 0, 1))
    # головка: самая дальняя вдоль оси точка
    vs = [v.Point for v in sh.Vertexes]
    top = max(vs, key=lambda p: p.dot(ax))
    # точка на оси: Placement.Base всех винтов стоит на их оси. Центр
    # BoundBox для этого не годится: у библиотечных винтов (B-сплайны после
    # transformGeometry) коробка считается по контрольным точкам и раздута
    c = pl.Base
    hp = c + ax * ((top - c).dot(ax))
    return ax, hp, sh


def screws(report=True):
    old = set_magnet(38.6)
    P = parts()
    set_magnet(old)
    issues = []
    rows = []
    for n, sh in sorted(P.items()):
        spec = next((s for s in SCREWS if n.startswith(s[0])), None)
        if spec is None:
            continue
        ax, hp, s = _screw_axis(sh)
        st = step_of(n)
        if n.startswith(SCREWS_SERVICE):
            # винт обслуживают на СОБРАННОМ роботе (натяжение ремня):
            # мешает всё, что есть
            before = {m: x for m, x in P.items() if m != n}
        else:
            before = {m: x for m, x in P.items() if step_of(m) <= st and m != n}
        # 1) путь головки: цилиндр R головки от торца наружу 12 мм
        head = Part.makeCylinder(spec[2] + 0.1, 12.0, hp + ax * 0.05, ax)
        # 2) ключ: цилиндр R ключа ещё на 60 мм
        key = Part.makeCylinder(spec[1], 60.0, hp + ax * 0.05, ax)
        hit_h = [m for m, x in before.items() if spec[3] and bb_hit(x, head)
                 and x.common(head).Volume > TOL]
        hit_k = [m for m, x in before.items() if bb_hit(x, key) and x.common(key).Volume > TOL]
        if hit_k and n.startswith(SCREWS_SERVICE):
            # Г-образный ключ: короткое плечо 15 мм по оси, длинное 50 мм
            # вбок — годится, если вбок свободно хотя бы в одну из 12 сторон
            leg = Part.makeCylinder(spec[1], 15.0, hp + ax * 0.05, ax)
            hit_leg = [m for m, x in before.items() if bb_hit(x, leg) and x.common(leg).Volume > TOL]
            e1 = ax.cross(V(1, 0, 0) if abs(ax.x) < 0.9 else V(0, 1, 0)); e1.normalize()
            e2 = ax.cross(e1)
            end = hp + ax * 15.0
            free_dir = None
            if not hit_leg:
                for k in range(12):
                    a = math.radians(30 * k)
                    dv = e1 * math.cos(a) + e2 * math.sin(a)
                    arm = Part.makeCylinder(spec[1], 50.0, end - ax * spec[1], dv)
                    if not [m for m, x in before.items() if bb_hit(x, arm)
                            and x.common(arm).Volume > TOL]:
                        free_dir = 30 * k
                        break
            if free_dir is not None:
                hit_k = []
            else:
                hit_k = hit_leg or hit_k
        ok = not hit_h and not hit_k
        rows.append((n, st, ok, hit_h, hit_k))
        if not ok:
            issues.append("винт %s (шаг сборки %d): %s%s" % (
                label(n), st,
                ("головка упирается в " + ", ".join(hit_h) + "; ") if hit_h else "",
                ("ключ упирается в " + ", ".join(hit_k)) if hit_k else ""))
    if report:
        print("SCREWS: винтов %d, без доступа %d" % (len(rows), len(issues)))
        for i in issues:
            print("   !!", i)
    return issues


# винты, которые крутят на собранном роботе: натяжение ремней — сдвигом
# плиты с мотором по пазам, винты плит к латунным стойкам
SCREWS_SERVICE = ("FR_PlScr",)


NUTS_CAPTIVE = ("CR_HolderNut", "EF_ClNut", "HW_Gayka", "EH_Gayka", "PV_Nut", "CAM_PlugNutM8",
                "CAM_HeadNut", "CAM_AxNut", "CAM_HubNut", "CAM_BrNut")
NUTS_OPEN = ("RD_Gayka", "CAM_PlugNut", "FR_ShaftNut")
# болты головкой в шестигранном гнезде: (болт, держатель) — не проворачиваются
BOLTS_HEX = (("FR_ShaftBolt", "FR_Column"),)


def _holder(P, n, sh):
    best, bv = None, 0
    big = sh.copy()
    big.scale(1.3, sh.BoundBox.Center)
    for m, x in P.items():
        if m == n or m.startswith(("FR_PlScr", "FR_ShaftBolt", "HW_Vint", "EH_Vint", "PV_Screw",
                                    "EF_ClScr", "CAM_PlugScr", "CAM_HeadScr", "CAM_AxBolt",
                                    "CAM_HubScr", "CAM_BrScr", "CAM_Mast", "CAM_Boom")):
            continue
        if not bb_hit(x, big):
            continue
        v = x.common(big).Volume
        if v > bv:
            best, bv = m, v
    return best


def nuts(report=True):
    old = set_magnet(38.6)
    P = parts()
    set_magnet(old)
    issues = []
    cnt = 0
    for n, sh in sorted(P.items()):
        if n.startswith(NUTS_CAPTIVE):
            cnt += 1
            h = _holder(P, n, sh)
            if h is None:
                issues.append("гайка %s ни в чём не сидит" % label(n))
                continue
            hs = P[h]
            hsb = hs.BoundBox
            ax = global_shape(D().getObject(n)).Placement.Rotation.multVec(V(0, 0, 1))
            c = sh.BoundBox.Center
            # 1) в гнезде без натяга
            v0 = hs.common(sh).Volume
            if v0 > TOL:
                issues.append("гайка %s: натяг в гнезде %s %.2f мм3" % (label(n), h, v0))
            # 2) не проворачивается: поворот на 20° даёт пересечение с держателем
            r = sh.copy()
            r.rotate(c, ax, 20.0)
            if hs.common(r).Volume < 0.5:
                issues.append("гайка %s проворачивается в %s — нет шестигранного гнезда" % (label(n), h))
            # 3) заводится: есть направление в плоскости гнезда, по которому
            #    гайка выходит наружу, ничего не задевая
            u = V(1, 0, 0) if abs(ax.x) < 0.9 else V(0, 1, 0)
            e1 = ax.cross(u); e1.normalize()
            e2 = ax.cross(e1)
            ok = False
            # направления: сетка 15° и вдоль граней/на вершины самой гайки —
            # паз всегда идёт по её граням, а гнездо может быть повёрнуто
            # вместе с деталью на любой угол (консоль камеры)
            rn = global_shape(D().getObject(n)).Placement.Rotation
            dirs = [e1 * math.cos(math.radians(15 * k)) + e2 * math.sin(math.radians(15 * k))
                    for k in range(24)]
            dirs += [rn.multVec(V(math.cos(math.radians(30 * k)), math.sin(math.radians(30 * k)), 0))
                     for k in range(12)]
            for dv in dirs:
                free = True
                for step in [0.5 * i for i in range(1, 41)]:
                    m = moved(sh, App.Placement(dv * step, App.Rotation()))
                    if not box_hit(m.BoundBox, hsb):
                        break
                    if hs.common(m).Volume > TOL:
                        free = False
                        break
                if free:
                    ok = True
                    break
            if not ok:
                for dv in (ax, ax * -1):         # гнездо, открытое вдоль оси
                    free = True
                    for step in [0.5 * i for i in range(1, 41)]:
                        m = moved(sh, App.Placement(dv * step, App.Rotation()))
                        if not box_hit(m.BoundBox, hsb):
                            break
                        if hs.common(m).Volume > TOL:
                            free = False; break
                    if free:
                        ok = True; break
            if not ok:
                issues.append("гайку %s не завести в гнездо %s" % (label(n), h))
        elif n.startswith(NUTS_OPEN):
            cnt += 1
            # рожковый ключ: «губки» — коробка 30 в длину в плоскости гайки
            # (ширина 10 под M3, 24 под M8), в одном из 12 направлений
            # свободна от всего, кроме своих деталей. Ось гайки — любая
            ax = global_shape(D().getObject(n)).Placement.Rotation.multVec(V(0, 0, 1))
            c = sh.BoundBox.Center
            hs_ = [v.Point.dot(ax) for v in sh.Vertexes]
            h0, h1 = min(hs_), max(hs_)
            c = c + ax * ((h0 + h1) / 2.0 - c.dot(ax))
            big = h1 - h0 > 5.0
            wj, rc = (24.0, 8.0) if big else (10.0, 4.0)
            u = V(1, 0, 0) if abs(ax.x) < 0.9 else V(0, 1, 0)
            e1 = ax.cross(u); e1.normalize()
            e2 = ax.cross(e1)
            ok = False
            for k in range(12):
                a = math.radians(30.0 * k)
                dv = e1 * math.cos(a) + e2 * math.sin(a)
                w = Part.makeBox(30.0, wj, h1 - h0, V(0, -wj / 2.0, -(h1 - h0) / 2.0))
                w = w.cut(Part.makeCylinder(rc, h1 - h0 + 2, V(0, 0, -(h1 - h0) / 2.0 - 1)))
                w.Placement = App.Placement(c, App.Rotation(dv, ax.cross(dv), ax, "ZXY"))
                hit = [m for m, x in P.items() if m != n and bb_hit(x, w) and x.common(w).Volume > TOL]
                if not hit:
                    ok = True
                    break
            if not ok:
                issues.append("к гайке %s не подлезть рожковым ключом" % label(n))
    # болты головкой в шестигранном гнезде: без натяга и не проворачиваются
    for n, h in BOLTS_HEX:
        if n not in P or h not in P:
            continue
        cnt += 1
        sh, hs = P[n], P[h]
        v0 = hs.common(sh).Volume
        if v0 > TOL:
            issues.append("болт %s: натяг в гнезде %s %.2f мм3" % (label(n), h, v0))
        pl = global_shape(D().getObject(n)).Placement
        r = sh.copy()
        r.rotate(pl.Base, pl.Rotation.multVec(V(0, 0, 1)), 20.0)
        if hs.common(r).Volume < 0.5:
            issues.append("болт %s проворачивается в %s — нет шестигранного гнезда" % (label(n), h))
    if report:
        print("NUTS: гаек %d, замечаний %d" % (cnt, len(issues)))
        for i in issues:
            print("   !!", i)
    return issues


# ---------------------------------------------------------------------------
# Вращающиеся друг относительно друга детали не должны касаться ничем,
# кроме подшипника: (ротор, [статоры]). Пересечение тут не поймать —
# касание даёт нулевой объём, поэтому меряем расстояние.
RUB_GAP = 0.2
RUB_PAIRS = [
    ("Body003", ["FR_ShaftBushLo", "FR_PlateA", "Body_Prost", "FR_ShaftBolt"]),
    ("Body_Pulley2", ["Body_Prost", "FR_ShaftBushHi", "FR_ShaftBolt", "Body003", "Body_Cap",
                      "FR_ShaftWash", "FR_ShaftNut", "CAM_Plug", "CAM_PlugNutM8"]),
    ("Body_Elbow2", ["Body_Elbow", "Body_ElbowCap", "PV_Screw", "PV_Nut"]),
    ("Body_Elbow2Cap", ["Body_ElbowCap", "Body_Elbow"]),
    ("Body_Rod", ["RD_VtulA", "RD_VtulB", "RD_ShaybaA", "RD_ShaybaB", "RD_GaykaA", "RD_GaykaB",
                  "RD_VintA", "RD_VintB", "Body_Pulley2", "Body_RodJoint", "Body_Cap",
                  "Body_ElbowCap", "Body_Elbow2"]),
    ("CR_GearSp", ["CR_Carriage"]), ("CR_Ext", ["CR_Carriage"]), ("CR_CupHolder", ["CR_Carriage", "CR_ServoR"]),
    ("CR_InnerSp", ["CR_Carriage"]), ("CR_Screw", ["CR_Carriage"]),
    ("CR_Carriage", ["EF_Bracket", "EF_ServoZ", "EF_Rail", "EF_RailScr"]),
    ("CR_Block", ["EF_Bracket", "EF_RailScr"]),
    ("CAM_Hub", ["CAM_Head", "CAM_SpIn", "CAM_SpTop", "CAM_AxBolt", "CAM_Mast", "CAM_Servo",
                 "CAM_SvScr", "CAM_HeadScr1", "CAM_HeadScr2"]),
    ("CAM_HubCap", ["CAM_Mast"]),
    ("CAM_Boom", ["CAM_AxBolt", "CAM_SpTop", "CAM_Mast"]),
]


def rubbing(report=True):
    P = parts()
    issues = []
    rows = []
    for rot, stators in RUB_PAIRS:
        if rot not in P:
            issues.append("нет детали %s" % rot)
            continue
        for st in stators:
            if st not in P:
                continue
            if not bb_hit(P[rot], P[st], 3.0):
                continue
            dmin = P[rot].distToShape(P[st])[0]
            rows.append((rot, st, dmin))
            if dmin < RUB_GAP:
                issues.append("%s касается %s (зазор %.2f мм) — трение мимо подшипника"
                              % (label(rot), label(st), dmin))
    if report:
        print("RUBBING: пар %d, касаний %d" % (len(rows), len(issues)))
        for r in rows:
            print("   %-16s - %-16s %.2f мм" % r)
        for i in issues:
            print("   !!", i)
    return issues


def gears(report=True):
    """Зацепление: межосевое по расчёту, зубья не входят друг в друга
    (с учётом бокового зазора) в нескольких положениях каретки."""
    issues = []
    lines = []
    for mz in (4.0, 13.0, 21.7, 30.0, 38.6):
        old = set_magnet(mz)
        P = parts()
        set_magnet(old)
        v1 = P["EF_GearZ"].common(P["CR_Carriage"]).Volume
        v2 = P["CR_GearSp"].common(P["CR_GearRt"]).Volume
        d1 = P["EF_GearZ"].distToShape(P["CR_Carriage"])[0]
        lines.append("магнит +%.1f: рейка/шестерня Z %.3f мм3 (зазор %.2f), шпиндель %.3f мм3"
                     % (mz, v1, d1, v2))
        if v1 > TOL:
            issues.append("шестерня Z врезается в рейку при магните +%.1f (%.2f мм3)" % (mz, v1))
        if v2 > TOL:
            issues.append("шестерни поворота врезаются друг в друга (%.2f мм3)" % v2)
        if d1 > 0.5:
            issues.append("шестерня Z не касается рейки при магните +%.1f (зазор %.2f)" % (mz, d1))
    if report:
        print("GEARS:")
        for l in lines:
            print("  ", l)
        for i in issues:
            print("   !!", i)
    return issues


# ---------------------------------------------------------------------------
MASS_FIXED = {"Body": 280.0, "Body001": 280.0, "EF_ServoZ": 9.0, "CR_ServoR": 9.0,
              "CAM_Servo": 9.0, "CAM_Board": 12.0, "CAM_Lens": 6.0,
              "CR_Magnet": 45.0, "CR_Cup1": 1.0, "CR_Cup2": 1.0, "CR_Cup3": 1.0, "FR_Belt1": 4.0, "FR_Belt2": 4.0,
              # электроника (elektronika_etz.FCMacro) — по паспортам/весам, г
              "EL_Board": 70.0, "EL_Drv1": 6.0, "EL_Drv2": 6.0, "EL_Esp": 10.0,
              "EL_DispPcb": 2.0, "EL_DispLcd": 2.0, "EL_VacSensor": 3.0,
              "EL_SB1": 1.0, "EL_SB2": 1.0, "EL_SB3": 1.0, "EL_Breadboard": 30.0,
              "EL_Pump": 60.0, "EL_Valve": 20.0, "EL_BatCells": 141.0, "EL_BatHolder": 25.0,
              "EL_Hall1": 1.0, "EL_Hall2": 1.0, "EL_MagS": 0.1, "EL_MagL": 0.1}
RHO = [(("FR_Base", "FR_Plate"), 0.65),              # фанера берёзовая
       (("FR_Std", "EL_PcbStd"), 8.5),                # латунные стойки
       (("EL_HallPost", "EL_HallBr"), 1.24 * 0.6),
       (("FR_Column", "CAM_Plug", "CAM_Head", "CAM_Hub", "CAM_Bracket",
         "CAM_GearSv", "EF_Bracket", "CR_Carriage", "Body003", "Body_Pulley2",
         "Body_Cap", "Body_Elbow", "Body_RodJoint", "Body_Rod", "EF_BracketCap", "CR_Gear",
         "EF_Gear", "Body_Prost", "CR_CupHolder"), 1.24 * 0.6),       # печать, заполнение ~60 %
       (("Body_Tube", "CAM_Mast", "CAM_Boom"), 2.7)]                          # алюминиевые трубы


def mass(report=True):
    g = geom()
    e = D().getObject("Etz")
    old = set_magnet(38.6)
    oc = set_cam(e.CamWork.Value)          # в работе консоль над полем — хуже для «перед»
    P = parts()
    set_cam(oc)
    set_magnet(old)
    fz = e.FloorZ.Value
    base_bb = P["FR_Base"].BoundBox

    def m_of(n, s):
        if n in MASS_FIXED:
            return MASS_FIXED[n]
        for pref, rho in RHO:
            if n.startswith(pref):
                return s.Volume / 1000.0 * rho
        if n == "Pulley" or n == "Driver2":
            return 8.0
        return s.Volume / 1000.0 * 7.85          # крепёж, подшипники — сталь

    issues = []
    worst = (1e9, None)
    M_ = {n: m_of(n, s) for n, s in P.items()}          # объём — один раз, не в каждой позе
    total = sum(M_.values())
    # перебор поз по всей рабочей зоне + шашка 7 г в захвате + запас
    # на разгон: горизонтальная сила 0.3 g на подвижные массы на высоте их ЦМ
    poses_ = [(t1, q2) for t1 in range(-110, 11, 10) for q2 in range(60, 157, 8)] + [PARK]
    for t1, q2 in poses_:
        if True:
            Pp = pose(P, g, t1, t1 + q2)
            ms = [(M_[n], s.BoundBox.Center if s.BoundBox.isValid() else V(), group_of(n) != "static")
                  for n, s in Pp.items()]
            Le_pt = None
            cm = V(0, 0, 0)
            M = 0.0
            for m, c, _ in ms:
                cm += c * m
                M += m
            # шашка
            S = g["S"]
            ex = S + V(g["L1"] * math.cos(math.radians(t1)) + g["Le"] * math.cos(math.radians(t1 + q2)),
                       g["L1"] * math.sin(math.radians(t1)) + g["Le"] * math.sin(math.radians(t1 + q2)), 0)
            cm += ex * 7.0
            M += 7.0
            cm = cm * (1.0 / M)
            # запас до каждого края основания с учётом разгона
            mov = sum(m for m, c, mv in ms if mv) + 7.0
            hz = 60.0                               # высота ЦМ подвижных частей над полем, ~
            dyn = 0.3 * mov * hz / M                # смещение ЦМ, эквивалентное разгону
            for edge, dist in (("перед", base_bb.XMax - cm.x), ("зад", cm.x - base_bb.XMin),
                               ("лево", cm.y - base_bb.YMin), ("право", base_bb.YMax - cm.y)):
                if dist - dyn < worst[0]:
                    worst = (dist - dyn, (edge, t1, q2, cm.x, cm.y))
    if worst[0] < 10.0:
        issues.append("запас устойчивости %.1f мм (край %s, поза t1=%d q2=%d) — мало"
                      % (worst[0], worst[1][0], worst[1][1], worst[1][2]))
    if report:
        print("MASS: всего ~%.0f г (с электроникой и аккумулятором)" % total)
        print("   худший запас ЦМ до края основания с учётом разгона 0.3g: %.1f мм (%s, t1=%d, q2=%d)"
              % (worst[0], worst[1][0], worst[1][1], worst[1][2]))
        for i in issues:
            print("   !!", i)
    return issues


LOG = None      # путь к файлу отчёта; None — только в консоль


def run(names=None, log=None):
    """Запустить проверки по именам (по умолчанию все) с выводом в файл.

    Через MCP длинный прогон не укладывается в таймаут запроса — поэтому
    отчёт пишется в файл построчно, и его можно читать, пока идёт расчёт.
    """
    import sys, time
    funcs = [static, bearings, rubbing, gears, tz, park, cam, sweep, sweep_cells, screws, nuts, mass]
    if names:
        funcs = [f for f in funcs if f.__name__ in names]
    old = sys.stdout
    fh = open(log, "w", encoding="utf-8", buffering=1) if log else None
    if fh:
        sys.stdout = fh
    res = {}
    _AXI_MEMO.clear()
    try:
        for f in funcs:
            t = time.time()
            try:
                res[f.__name__] = f()
            except Exception:
                import traceback
                traceback.print_exc(file=sys.stdout)
                res[f.__name__] = ["ОШИБКА выполнения"]
            print("   (%s: %.0f с)" % (f.__name__, time.time() - t))
        print("")
        print("ИТОГ:", ", ".join("%s %s" % (k, "OK" if not v else "%d замеч." % len(v))
                                for k, v in res.items()))
        print("ГОТОВО")
    finally:
        sys.stdout = old
        if fh:
            fh.close()
    return res


def run_all():
    return run()


if __name__ == "__main__":
    run_all()
