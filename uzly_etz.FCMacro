# -*- coding: utf-8 -*-
# uzly_etz.FCMacro
#
# Всё, чего не хватало приводу руки до устройства по ЕТЗ 2026-27:
#
#   * СТАНИНА: основание — фанера 6 мм, на ней небольшие печатные стойки
#     (5 под плиты моторов + стойка вала) на вставках M3 и потайных винтах
#     снизу; плиты моторов, вал M8 со втулками — стопка внутренних колец
#     608ZZ и проставки зажата болтом, шкивы крутятся только на наружных
#     кольцах. Натяжение ремней — сдвигом плит по пазам.
#   * РЕМНИ GT2 обеих ступеней (огибающая по шкивам) — чтобы проверять
#     зазоры до них, а не на глаз.
#   * РАБОЧИЙ УЗЕЛ на конце предплечья: кронштейн-хомут с T-направляющей,
#     каретка Z на рейке (SG90 + шестерня z22, ход 34.6 мм за 180°),
#     шпиндель на двух 625ZZ, вакуумный захват — присоска DP8 на печатном
#     держателе, поворот 0..360° через передачу 13 -> 26 от второго SG90
#     (180° серво = 360° захвата).
#   * ПОЛИГОН-ссылка: зоны, лист поля и центры клеток в координатах робота
#     — для проверки ТЗ прямо в этом документе.
#
# Размеры берутся из VarSet `Drive` (привод) и `Etz` (этот макрос) В МОМЕНТ
# ЗАПУСКА: геометрия деталей — Part::Feature, её надо пересобрать этим
# макросом после правки Drive. Положения, зависящие от позы (угол
# предплечья, высота захвата), привязаны выражениями и меняются сами.
#
# Проверка всего этого — proverka_etz.FCMacro.
#
# Запуск: после shkiv_param.FCMacro, тем же exec(...).

import math

import FreeCAD as App
import Part

DOC_HINT = "ETZ_Robot"
VS = "Drive"
VE = "Etz"

FRAME_PART = "Part_Frame"      # App::Part станины (глобальные координаты)
EFF_PART = "Part_Eff"          # рабочий узел, внутри Part_Tube, крутится с предплечьем
CARR_PART = "Part_Carr"        # каретка Z, внутри Part_Eff, едет по высоте
POLY_GROUP = "Poly_Ref"        # полигон-ссылка

# ---------------------------------------------------------------------------
# Переменные этого макроса (VarSet Etz). Значения пользователя не затираются.
# ---------------------------------------------------------------------------
INPUTS = [
    ("PolyShaftX", "App::PropertyLength", "1 Полигон", 300.0,
     "X оси шкивов (плеча) в координатах ПОЛИГОНА (п. 2.1 ЕТЗ: 0 — левый "
     "нижний угол). Зона 1 — x 0..350"),
    ("PolyShaftY", "App::PropertyLength", "1 Полигон", 235.0,
     "Y оси плеча на полигоне. Ниже середины поля (252.5) на 17.5 мм: так "
     "рука паркуется над нижней полосой зоны 2 с запасом, а дальние клетки "
     "у отбоя всё ещё в 60+ градусах от сингулярности"),
    ("FloorZ", "App::PropertyDistance", "1 Полигон", -7.0,
     "Поверхность полигона в координатах робота. Низ левого мотора — z 0, "
     "под ним 1 мм зазора и основание 6 мм"),
    ("MagnetZ", "App::PropertyLength", "2 Поза", 30.0,
     "Высота рабочей грани захвата (губы присоски) над полем. 5 = касается "
     "шашки, лежащей на поле (4 — поджата на 1 мм); 25 = верх стопки из 5"),
    ("BaseT", "App::PropertyLength", "3 Станина", 6.0, "Толщина основания"),
    ("PlateAT", "App::PropertyLength", "3 Станина", 6.0,
     "Толщина плиты мотора 1 — фанера (плита мотора 2 — Drive.Plate2T)"),
    ("BaseX0", "App::PropertyDistance", "3 Станина", -75.0,
     "Задний край основания (x робота). Чем дальше назад — тем устойчивее"),
    ("BaseFront", "App::PropertyLength", "3 Станина", 45.0,
     "Передний край основания — на столько впереди оси шкивов. Ось на "
     "полигоне x = PolyShaftX (300), граница зоны 1 — x 350"),
    ("BaseY0", "App::PropertyDistance", "3 Станина", -90.0, "Левый край основания"),
    ("BaseY1", "App::PropertyDistance", "3 Станина", 135.0, "Правый край основания"),
    ("BaseRearX0", "App::PropertyDistance", "3 Станина", -185.0,
     "Удлинение основания назад под электронику (за моторами): задний край. "
     "На полигоне x = PolyShaftX + (BaseRearX0 - ось шкивов) — не меньше 3 (зона 1)"),
    ("BaseRearY0", "App::PropertyDistance", "3 Станина", -205.0, "Удлинение назад: левый край"),
    ("BaseRearY1", "App::PropertyDistance", "3 Станина", -25.0,
     "Удлинение назад: правый край. Дальше по y — захват на парковке (висит у y +15)"),
    ("TensionSlot", "App::PropertyLength", "3 Станина", 2.0,
     "Ход натяжения ремня в каждую сторону (пазы плит под винты стоек)"),
    ("CamStow", "App::PropertyAngle", "4 Камера", 95.0,
     "Угол консоли в сложенном виде (до старта и после финиша): камера над "
     "зоной 1. Мачта на оси шкивов, консоль ~155 мм: при 95° край кронштейна "
     "камеры — на x ~340 полигона, SG90 — 165° (i = 2)"),
    ("CamAngle", "App::PropertyAngle", "4 Камера", 95.0,
     "ПОЗА: текущий угол консоли. CamStow — сложена, CamWork — камера над "
     "центром поля"),
    ("CamWork", "App::PropertyAngle", "4 Камера", 17.8,
     "Угол консоли в работе — считает макрос (направление на центр листа)"),
    ("CamLensH", "App::PropertyLength", "4 Камера", 327.0,
     "Высота объектива над полем. Голова зажата на мачте разрезным хомутом "
     "и ставится на любую высоту — мачта может быть длиннее и торчать выше"),
]


def ensure_vs(doc):
    vs = doc.getObject(VE)
    if vs is None:
        vs = doc.addObject("App::VarSet", VE)
        vs.Label = "Etz"
    for name, typ, grp, default, tip in INPUTS:
        if not hasattr(vs, name):
            vs.addProperty(typ, name, grp, tip)
            setattr(vs, name, default)
    return vs


# ---------------------------------------------------------------------------
# Константы покупных деталей (по стандарту / паспорту)
# ---------------------------------------------------------------------------
NEMA_HALF = 21.15            # полугабарит корпуса 42.3
NEMA_PCD = 31.0              # квадрат резьбовых отверстий M3
NEMA_BOSS = 22.0             # центрирующий буртик Ø22 x 2

M3 = dict(d=3.0, dk=5.5, k=3.0, s=2.5, nut_s=5.5, nut_m=2.4, hole=3.4)
M4 = dict(d=4.0, dk=7.0, k=4.0, s=3.0, nut_s=7.0, nut_m=3.2, hole=4.4)
M5 = dict(d=5.0, dk=8.5, k=5.0, s=4.0, nut_s=8.0, nut_m=4.7, hole=5.5)
M8 = dict(d=8.0, dk=13.0, k=8.0, s=6.0, nut_s=13.0, nut_m=6.8, hole=8.4)

BRG625 = dict(d=5.0, D=16.0, B=5.0, d1=7.5)     # 625ZZ, d1 — Ø внутр. кольца
BRG608_D1 = 12.1                                 # Ø внутреннего кольца 608ZZ

# вакуумный захват: 1 присоска DP8 на оси шпинделя (сильфон 1.5 гофра, чертёж — Screenshot_20261101-164036):
# высота 15, верх Ø12, губа Ø8, канал Ø2. Гнездо сверху: ВХОД Ø4.2 x 3, под ним
# расширение Ø6.8 x 2 — присоска защёлкивается на штуцер-грибок
CUP_H, CUP_TOP_R, CUP_LIP_R = 15.0, 6.0, 4.0
CUP_SOCK = ((4.2, 3.0), (6.8, 2.0))           # гнездо присоски сверху вниз: (Ø, глубина)
HEAD_CH = 0.6                 # заходная фаска на головке грибка (проходит вход Ø4.2)
HOLD_R, HOLD_Z0, HOLD_Z1 = 9.0, CUP_H, 27.0    # держатель присоски (печать)
CH_Z = HOLD_Z0 + 1.8          # ось поперечного вакуумного канала: штуцер присоски -> штуцер трубки
NIP_BORE = 1.0                # канал в штуцере под присоску, R (Ø2 — как канал присоски; Ø1.6 FDM затягивает)
BARB_A, BARB_R1 = 270.0, HOLD_R + 6.0   # штуцер-ёлочка под силикон 3x5: направление, конец (R от оси);
                                         # сзади на R23.5 рельс

# SG90 (модель из библиотеки): ось выхода (0, 16.6), торец шлица z 29.9,
# лапки z 15.9..18.4, отверстия лапок y -2.35 и 24.85
SG_AXIS_Y, SG_TAB_Z0, SG_TAB_Z1 = 16.6, 15.9, 18.4
SG_HOLES_Y = (-2.35, 24.85)
SG_GEAR_Z = 27.0             # низ шестерни, надетой на шлиц (над буртиком 26.7)

# --- рабочий узел, фрейм предплечья (x от оси локтя, z — как в Part_Tube) ---
CL_X0, CL_X1 = 94.0, 120.0   # хомут кронштейна на трубе 2 (труба кончается на 120)
CL_SCREW_X = (100.0, 114.0)
GP_X0, GP_X1, GP_HW = 120.0, 126.0, 16.0          # пластина направляющей
# --- покупная линейная направляющая MGN9 (рельс) + MGN9H (каретка) ---
# размеры по каталогу HIWIN / совместимых (KGT и т. п.):
# рельс 9 x 6.5, отверстия под M3 с цековкой Ø6 x 3.5, шаг 20, от торца 10;
# каретка H = 10 (от низа рельса до опорной грани), H1 = 2.2, W = 20,
# L = 39.9 (с уплотнениями), крепёж 4 x M3 x 3 по 15 (поперёк) x 16 (вдоль)
RAIL_W, RAIL_H, RAIL_L, RAIL_P, RAIL_E = 9.0, 6.5, 100.0, 20.0, 10.0
RAIL_CB_D, RAIL_CB_H, RAIL_HOLE = 6.0, 3.5, 3.5
BLK_H, BLK_H1, BLK_W, BLK_L, BLK_B, BLK_C = 10.0, 2.2, 20.0, 39.9, 15.0, 16.0
RAIL_X0 = GP_X1                                    # рельс лежит на пластине
BLK_FACE = RAIL_X0 + BLK_H                         # опорная грань каретки MGN9H
INSERT_D, INSERT_L = 4.6, 5.0                      # резьбовая вставка M3 в пластике
SP_X0, SP_X1, SP_HW = BLK_FACE, BLK_FACE + 5.0, 12.0   # печатная плита каретки Z
SP_Z0, SP_Z1 = 33.0, 78.0                          # рейка от грани магнита
BLK_ZC = 70.0      # центр каретки MGN9H от грани магнита: её винты выше корпуса
                   # шпинделя и шестерни, иначе к ним спереди не подлезть
SP_TOP = BLK_ZC + BLK_L / 2.0 + 2.0                # верх плиты каретки
SPINDLE_X = 156.0                                  # ось шпинделя = вылет захвата
HOUS_R, HOUS_Z0, HOUS_Z1 = 10.5, 33.0, 53.0         # корпус шпинделя
EXT_H = HOUS_Z0 - HOLD_Z1                          # удлинитель держатель -> подшипник (6)
GEAR_M = 1.0
ZP_TEETH = 22                                      # шестерня оси Z (на SG90 №1)
SPG_TEETH, SPG_SHIFT = 26, -0.3                    # шестерня шпинделя
RTP_TEETH, RTP_SHIFT = 13, +0.3                    # шестерня SG90 №2 (поворот)
GEAR_W = 5.0
SERVO_FLANGE_X = SP_X0 + 18.4 - 27.0   # опорная грань лапок SG90 №1: шестерня Z
                                       # встаёт ровно в полосу рейки на плите каретки
Z_STROKE = math.pi * GEAR_M * ZP_TEETH / 2.0       # 180° серво: pi * r

# --- камера на откидной консоли ---
SHEET_C = (475.0, 250.0)          # центр листа А4 на полигоне (ETZ_poligon)
MAST_D, MAST_T, MAST_L = 16.0, 1.5, 260.0          # мачта: Al труба Ø16x1.5 x 260 на оси шкивов (голова на любой высоте)
PLUG_R, PLUG_FL, PLUG_SPIG = 11.0, 9.0, 25.0       # пробка мачты: фланец R11 x 9 (гайка M8 внутри), хвостовик 25 в трубу
PLUG_ENGAGE = 6.0                                  # резьба болта вала в гайке пробки, не меньше
CAM_OFF = 30.0                    # ось консоли вынесена вбок от оси мачты
HUB_HL, HUB_HW = 19.0, 11.5       # хомут консоли на ступице: полудлина, полуширина
HUB_SY, HUB_SX = 7.8, 13.5        # винты хомута консоли: от оси трубы поперёк / вдоль
HUB_CAP = 8.0                     # крышка хомута консоли над осью трубы
HUB_GAP = 0.3                     # зазор крышка — седло: есть что затягивать
SLEEVE_H = 40.0                   # хомут головы на мачте
BOOM_D, BOOM_T = 10.0, 1.0                         # консоль: Al труба Ø10x1 (как рука)
CAM_GEAR_HUB, CAM_GEAR_SV = 26, 13                 # z26 на ступице <- z13 на SG90 (i = 2, как поворот захвата)
CAM_PCB, CAM_HOLE = 38.0, 34.0    # плата USB-камеры 38x38, крепёж M2 по 34x34
CAM_FOV_H, CAM_FOV_V = 60.0, 47.0                  # IMX179 AF: H 60°, V 47° (4:3)


# ---------------------------------------------------------------------------
# Геометрия-помощники
# ---------------------------------------------------------------------------
V = App.Vector


def box(x0, x1, y0, y1, z0, z1):
    return Part.makeBox(x1 - x0, y1 - y0, z1 - z0, V(x0, y0, z0))


def cyl(r, z0, z1, x=0.0, y=0.0):
    return Part.makeCylinder(r, z1 - z0, V(x, y, z0))


def cyl_x(r, x0, x1, y=0.0, z=0.0):
    return Part.makeCylinder(r, x1 - x0, V(x0, y, z), V(1, 0, 0))


def tube(ro, ri, z0, z1, x=0.0, y=0.0):
    return cyl(ro, z0, z1, x, y).cut(cyl(ri, z0 - 1, z1 + 1, x, y))


def hexagon(s, z0, z1, x=0.0, y=0.0, rot=0.0):
    """Шестигранник «под ключ s». rot=0: вершины на ±Y, грани ⟂ X —
    так гайка скользит вдоль Y по пазу шириной s."""
    rc = s / math.sqrt(3.0)
    pts = [V(x + rc * math.cos(math.radians(90 + rot + 60 * i)),
             y + rc * math.sin(math.radians(90 + rot + 60 * i)), z0) for i in range(7)]
    return Part.Face(Part.makePolygon(pts)).extrude(V(0, 0, z1 - z0))


def rounded_rect(x0, x1, y0, y1, z0, z1, r):
    b = box(x0 + r, x1 - r, y0, y1, z0, z1).fuse(box(x0, x1, y0 + r, y1 - r, z0, z1))
    for cx in (x0 + r, x1 - r):
        for cy in (y0 + r, y1 - r):
            b = b.fuse(cyl(r, z0, z1, cx, cy))
    return b.removeSplitter()


def slot(r, z0, z1, p, u, half):
    """Паз: окружность r, протянутая на ±half вдоль единичного u."""
    a = V(p.x - u.x * half, p.y - u.y * half, 0)
    b = V(p.x + u.x * half, p.y + u.y * half, 0)
    s = cyl(r, z0, z1, a.x, a.y).fuse(cyl(r, z0, z1, b.x, b.y))
    n = V(-u.y, u.x, 0)
    pts = [a + n * r, b + n * r, b - n * r, a - n * r, a + n * r]
    pts = [V(q.x, q.y, z0) for q in pts]
    s = s.fuse(Part.Face(Part.makePolygon(pts)).extrude(V(0, 0, z1 - z0)))
    return s.removeSplitter()


def soften(shape, r, zs, name):
    """Скруглить периметр детали на высотах zs (п. 3.2 ЕТЗ: кромки
    скруглены). Берётся внешний контур верхних граней на высотах zs; если
    ядро не справилось — деталь остаётся как есть и в отчёт идёт строка."""
    edges = []
    for f in shape.Faces:
        if f.Surface.__class__.__name__ != "Plane":
            continue
        n = f.normalAt(0, 0)
        c = f.CenterOfMass
        if n.z > 0.99 and any(abs(c.z - z) < 1e-6 for z in zs):
            edges += f.OuterWire.Edges
    for rr in (r, r / 2.0, r / 4.0):      # на коротких рёбрах большой радиус не встаёт
        try:
            f = shape.makeFillet(rr, edges)
            if f.isValid() and abs(f.Volume - shape.Volume) < 0.02 * shape.Volume:
                return f
        except Exception:
            pass
    print("  !! %s: скругление кромок не построилось, деталь без него" % name)
    return shape


def cap_screw(m, L):
    """ISO 4762: опорная грань головки на z = 0, головка вверх, стержень вниз."""
    head = cyl(m["dk"] / 2.0, 0.0, m["k"])
    key = hexagon(m["s"], m["k"] - 0.6 * m["s"], m["k"] + 0.1)
    return head.cut(key).fuse(cyl(m["d"] / 2.0, -L, 0.0)).removeSplitter()


CSK_DK, CSK_K = 6.0, 1.5    # ISO 10642 M3 (90°): головка Ø6
CSK_SINK = 0.6              # головка утоплена в фанеру на 0.6 — поля касается только фанера
CSK_L = 10                  # фанера 6 + 4 мм в вставку M3x5


def csk_screw(m, L):
    """ISO 10642: торец головки на z = 0, головка «вверх» (+Z локально),
    конус и стержень вниз. Длина — с головкой."""
    head = Part.makeCone(CSK_DK / 2.0, m["d"] / 2.0, CSK_K, V(0, 0, 0), V(0, 0, -1))
    head = head.cut(hexagon(m["s"], -1.2, 0.1))
    return head.fuse(cyl(m["d"] / 2.0, -L, -CSK_K + 0.01)).removeSplitter()


BTN_DK, BTN_K, BTN_S = 5.7, 1.65, 2.0   # ISO 7380 M3: полукруглая головка, ключ 2


def button_screw(m, L):
    """ISO 7380 (головка упрощена до цилиндра): опорная грань на z = 0,
    головка вверх, стержень вниз. Только M3."""
    head = cyl(BTN_DK / 2.0, 0.0, BTN_K).cut(hexagon(BTN_S, BTN_K - 1.0, BTN_K + 0.1))
    return head.fuse(cyl(m["d"] / 2.0, -L, 0.0)).removeSplitter()


M8_HEAD_S, M8_HEAD_K, M8_THREAD = 13.0, 5.3, 22.0  # DIN 931 M8: шестигранник 13, головка 5.3, резьба 22 (L <= 125)
WASH8_D, WASH8_S = 16.0, 1.6                       # шайба M8 DIN 125


def hex_bolt(m, L):
    """DIN 931 M8: опорная грань головки на z = 0, головка ВНИЗ, стержень вверх."""
    return hexagon(M8_HEAD_S, -M8_HEAD_K, 0.0, rot=90.0).fuse(cyl(m["d"] / 2.0, -0.01, L)).removeSplitter()


def shaft_nut_top(d):
    """Верх гайки, стягивающей стопку вала сверху (на ней — пробка мачты камеры)."""
    zt = d.BeltPlaneZ.Value - d.FlangeThk.Value + d.BrgZ2.Value + d.BrgW2.Value
    return zt + 4.0 + WASH8_S + M8["nut_m"]


# латунная стойка M3 «мама-мама» и шайба DIN 125
STD_S, STD_BORE = 5.5, 2.5          # под ключ 5.5; резьба M3 (в модели — Ø2.5 под метчик)
STD_THREAD = 4.0                    # минимум резьбы винта в стойке
STD_L = (5, 6, 8, 10, 12, 15, 20, 25, 30, 35, 40, 45, 50)
WASH_D, WASH_S = 7.0, 0.5


def nut(m, rot=0.0):
    """ISO 4032: низ на z = 0. rot как у hexagon()."""
    return hexagon(m["nut_s"], 0.0, m["nut_m"], rot=rot).cut(cyl(m["d"] / 2.0, -1, m["nut_m"] + 1))


def nut_pocket(m, z0, x, y, slide, rot=0.0, depth=30.0):
    """Гнездо гайки + боковой паз для заводки. slide — единичный вектор
    наружу (куда открыт паз), паз шириной «под ключ» + 0.3."""
    s = m["nut_s"] + 0.3
    h = m["nut_m"] + 0.4
    p = hexagon(s, z0, z0 + h, x, y, rot)
    ang = math.degrees(math.atan2(slide.y, slide.x))
    sl = box(0, depth, -s / 2.0, s / 2.0, z0, z0 + h)
    sl.rotate(V(0, 0, 0), V(0, 0, 1), ang)
    sl.translate(V(x, y, 0))
    return p.fuse(sl)


def involute_gear(m, z, w, bore=0.0, shift=0.0, backlash=0.12, z0=0.0, steps=6,
                  plane="xy", phase=0.0):
    """Прямозубое эвольвентное колесо, угол 20°, со смещением shift.

    plane="xy": ось колеса Z, толщина z0..z0+w, зуб 0 смотрит по углу phase
    от +X. plane="yz": ось колеса X, толщина x0..x0+w (x0 = z0), угол
    phase отсчитывается от +Y к +Z. Ось сразу строится нужная: поворот,
    сделанный rotate() у формы, живёт в её Placement и пропадает, как
    только детали присваивают свой Placement.
    """
    a = math.radians(20.0)
    rp = m * z / 2.0
    rb = rp * math.cos(a)
    ra = rp + m * (1.0 + shift)
    rf = rp - m * (1.25 - shift)
    inv = lambda t: math.tan(t) - t
    s = m * (math.pi / 2.0 + 2.0 * shift * math.tan(a)) - backlash
    half_p = s / (2.0 * rp)
    r0 = max(rb, rf)
    rs = [r0 + (ra - r0) * i / float(steps) for i in range(steps + 1)]
    fl = [(r, half_p + inv(a) - inv(math.acos(min(1.0, rb / r)))) for r in rs]
    th_base = fl[0][1]
    pts = []
    ph = math.radians(phase)
    for i in range(z):
        c = 2.0 * math.pi * i / z + ph
        tooth = [(rf, c - th_base)] + [(r, c - t) for r, t in fl] + \
                [(r, c + t) for r, t in reversed(fl)] + [(rf, c + th_base)]
        if plane == "yz":
            pts += [V(z0, r * math.cos(t), r * math.sin(t)) for r, t in tooth]
        else:
            pts += [V(r * math.cos(t), r * math.sin(t), z0) for r, t in tooth]
    pts.append(pts[0])
    if plane == "yz":
        g = Part.Face(Part.makePolygon(pts)).extrude(V(w, 0, 0))
        if bore > 0:
            g = g.cut(cyl_x(bore / 2.0, z0 - 1, z0 + w + 1))
    else:
        g = Part.Face(Part.makePolygon(pts)).extrude(V(0, 0, w))
        if bore > 0:
            g = g.cut(cyl(bore / 2.0, z0 - 1, z0 + w + 1))
    return g


def rack(m, length, w, z0, back):
    """Рейка вдоль Z: делительная прямая на y = 0, зубья в +y, основание
    до y = -back. Толщина w по X от 0. Зубья трапецией 20° (эвольвента рейки)."""
    p = math.pi * m
    ha, hf = m, 1.25 * m
    t = math.tan(math.radians(20.0))
    n = int(length / p) + 1
    prof = [V(0, -back, z0)]
    for i in range(n):
        zc = z0 + p * (i + 0.5)
        # зуб: ширина p/2 на делительной прямой
        prof += [V(0, -hf, zc - p / 4 - hf * t), V(0, ha, zc - p / 4 + ha * t),
                 V(0, ha, zc + p / 4 - ha * t), V(0, -hf, zc + p / 4 + hf * t)]
    prof += [V(0, -back, z0 + n * p), V(0, -back, z0)]
    # подрезать до length
    f = Part.Face(Part.makePolygon(prof)).extrude(V(w, 0, 0))
    return f.common(box(-1, w + 1, -back - 1, ha + 1, z0, z0 + length))


def lib_feature(rel):
    """Деталь из parts_library как есть (форма + её Placement)."""
    import os
    path = os.path.join(App.getUserAppDataDir(), "Mod", "parts_library", rel)
    if not os.path.exists(path):
        return None
    d = App.openDocument(path, True)
    try:
        best = None
        for o in d.Objects:
            sh = getattr(o, "Shape", None)
            if sh is None or sh.isNull() or sh.Volume < 1e-9:
                continue
            best = o.Shape.copy()
        return best
    finally:
        App.closeDocument(d.Name)


def sg90():
    sh = lib_feature("Electrical Parts/Servos/SG-90/Servo sg90.fcstd")
    if sh is None:      # габаритная замена
        sh = box(-5.9, 5.9, 0, 22.5, 0, 22.7).fuse(box(-5.9, 5.9, -4.7, 27.7, 15.9, 18.4))
        sh = sh.fuse(cyl(2.4, 22.7, 29.9, 0, SG_AXIS_Y))
        sh = sh.cut([cyl(1.1, SG_TAB_Z0 - 1, SG_TAB_Z1 + 1, 0, ys) for ys in SG_HOLES_Y])  # лапки
    sh = sh.copy()
    m = sh.Placement.toMatrix()
    sh.Placement = App.Placement()
    return sh.transformGeometry(m) if not m.isUnity() else sh


# ---------------------------------------------------------------------------
# Документ-помощники
# ---------------------------------------------------------------------------
def pick_doc():
    act = App.ActiveDocument
    if act is not None and act.getObject(VS) is not None:
        return act
    for d in App.listDocuments().values():
        if d.getObject(VS) is not None:
            return d
    raise RuntimeError("не нашёл документ с VarSet " + VS)


def purge(doc, prefixes):
    for o in list(doc.Objects):
        if o.Name.startswith(prefixes) and doc.getObject(o.Name) is not None:
            doc.removeObject(o.Name)


def feat(doc, part, name, label, shape, color, alpha=0):
    o = doc.addObject("Part::Feature", name)
    o.Shape = shape
    o.Label = label
    part.addObject(o)
    if App.GuiUp:
        o.ViewObject.ShapeColor = color
        o.ViewObject.DiffuseColor = [color]
        o.ViewObject.Transparency = alpha
    return o


def container(doc, name, label, parent=None):
    p = doc.getObject(name)
    if p is None:
        p = doc.addObject("App::Part", name)
        if parent is not None:
            parent.addObject(p)
    p.Label = label
    return p


PLA = (0.93, 0.55, 0.15)       # печатные детали станины
PLY = (0.86, 0.74, 0.52)       # фанера
BRASS = (0.85, 0.70, 0.30)     # латунные стойки
PLA2 = (0.25, 0.55, 0.85)      # печатные детали рабочего узла
STEEL = (0.62, 0.64, 0.67)
DARK = (0.30, 0.32, 0.35)
BELT = (0.12, 0.12, 0.12)
SERVO = (0.15, 0.35, 0.80)


# ---------------------------------------------------------------------------
# Станина
# ---------------------------------------------------------------------------
def build_frame(doc, d, e):
    """Основание и плиты моторов (фанера), латунные стойки, стойка вала. Глобальные координаты.

    Левый мотор ПЕРЕВЁРНУТ: стоит фланцем вниз на плите 1, вал вниз,
    ведущий шкив под плитой на уровне венца ведомого. Правый — валом
    ВВЕРХ: висит под плитой 2 на своих 4 винтах, шкив над плитой на
    уровне венца шкива 2. Обе плиты лежат на покупных латунных стойках
    M3, привинченных к основанию снизу.
    """
    purge(doc, ("FR_",))
    part = container(doc, FRAME_PART, "Станина")

    S = V(d.PulleyAxisX.Value, d.ArmAxisY.Value, 0)
    Z0 = d.BeltPlaneZ.Value - d.FlangeThk.Value          # низ шкива 1
    M1 = V(0, 0, 0)
    M2 = V(d.Motor2X.Value, d.Motor2Y.Value, 0)
    face1, face2 = d.Motor1FaceZ.Value, d.Motor2FaceZ.Value
    fl = e.FloorZ.Value
    top = fl + e.BaseT.Value                               # верх основания
    tA, tB = e.PlateAT.Value, d.Plate2T.Value
    zA0, zA1 = face1 - tA, face1                           # плита 1 ПОД фланцем мотора 1
    zB0, zB1 = face2, face2 + tB                           # плита 2 НАД фланцем мотора 2
    ymid = (M1.y + NEMA_HALF + M2.y - NEMA_HALF) / 2.0     # середина щели между моторами
    u1 = (S - M1); u1.normalize()                          # направление натяжения ремня 1
    u2 = (S - M2); u2.normalize()
    slot_h = e.TensionSlot.Value
    bush_lo = 2.5
    col_top = Z0 - bush_lo                                 # колонна вала: до нижней втулки
    # над плитами ходит глаз тяги: R57.5 от оси шкивов + 4 мм + ход натяжения
    rod_keep = 61.5 + slot_h
    PARK_T1_MAX, PARK_KEEP = 140.0, 7.0    # плечо на парковке 136 ± 2 (+2 запаса); R трубы 5 + 2

    # --- ОСНОВАНИЕ — ФАНЕРА 6 мм (лобзик/фрезер, сверловка по шаблону).
    #     На ней — латунные стойки плит моторов и печатная стойка вала.
    #     Всё притянуто СНИЗУ потайными винтами (головки утоплены в
    #     зенковки, низ фанеры гладкий — робот стоит на полигоне ровно).
    base = rounded_rect(e.BaseX0.Value, S.x + e.BaseFront.Value, e.BaseY0.Value, e.BaseY1.Value,
                        fl, top, 8.0)
    if e.BaseRearX0.Value < e.BaseX0.Value - 1.0:
        # удлинение назад под плату электроники: за моторами, в стороне от
        # захвата на парковке; заходит под основное на 10 мм — одна деталь
        rear = rounded_rect(e.BaseRearX0.Value, e.BaseX0.Value + 10.0, e.BaseRearY0.Value,
                            e.BaseRearY1.Value, fl, top, 8.0)
        base = base.fuse(rear).removeSplitter()
    foot_t = 7.0                                           # подошва стойки вала: вставка 5 + 2
    col_r = 12.0
    col_f = 17.0                                           # полуширина подошвы стойки вала
    col_ins = [(S.x + sx * 12.0, S.y + sy * 12.0) for sx in (-1, 1) for sy in (-1, 1)]

    # --- стойки плит: покупные латунные шестигранные M3 «мама-мама»
    #     (под ключ 5.5) стандартной длины; недостающее до плиты добирают
    #     шайбы DIN 125 под стойкой. Снизу — потайной винт сквозь фанеру,
    #     сверху — винт с полукруглой головкой ISO 7380 сквозь паз плиты.
    #     Стойки 1 — те же точки, что винты прежних печатных стенок (над
    #     ними тяга проходит с запасом); стойки 2 — вокруг корпуса мотора 2,
    #     он висит под плитой между ними. Передняя стойка 2 — между ремнём 2
    #     (иначе к её винту не подлезть ключом) и трубой плеча на парковке.
    stA = [V(-30.1, -30.1, 0), V(12.0, -30.1, 0), V(-30.1, 12.65, 0)]
    stB = [V(-20.0, 30.0, 0), V(-20.0, 74.0, 0), V(12.0, 74.0, 0), V(41.0, 59.0, 0)]

    def stack(h):
        """Стойка стандартной длины + 0..2 шайбы 0.5 под ней — ровно h."""
        for L in sorted(STD_L, reverse=True):
            n = int(round((h - L) / WASH_S))
            if 0 <= n <= 2 and abs(h - L - n * WASH_S) < 0.01:
                return L, n
        raise RuntimeError("стойка %.2f мм: не набирается из стандартных длин" % h)

    def screw_len(need):
        return next(L for L in (6, 8, 10, 12, 16, 20) if L >= need)

    stands = []        # (точка, высота стойки, шайб, паз вдоль, плита: z низа, толщина)
    for pts, z0p, t, u in ((stA, zA0, tA, u1), (stB, zB0, tB, u2)):
        L, nw = stack(z0p - top)
        for p in pts:
            stands.append((p, L, nw, u, z0p, t))

    # вал M8: болт DIN 931 СНИЗУ, головкой в шестигранном гнезде на дне
    # колонны (снизу гнездо закрывает фанера) — болт не проворачивается.
    # Стопку стягивает гайка сверху, а на конец болта над ней навинчена
    # пробка мачты камеры: момент от мачты уходит через головку в колонну,
    # а не в затяжку стопки. Длина — самая короткая стандартная, при
    # которой резьба над гайкой стопки входит в гайку пробки на PLUG_ENGAGE
    z_hb = top + M8_HEAD_K + 0.4                          # опорная грань головки — потолок гнезда
    z_nt = shaft_nut_top(d)
    bolt_L = next((L for L in (60, 65, 70, 75, 80, 90, 100) if z_hb + L >= z_nt + PLUG_ENGAGE), None)
    if bolt_L is None:
        raise RuntimeError("вал M8: болта нужной длины нет")
    if z_hb + bolt_L - M8_THREAD > z_nt - M8["nut_m"]:
        raise RuntimeError("вал M8x%d: резьба кончается выше гайки стопки" % bolt_L)
    if col_top - z_hb < 4.0:
        raise RuntimeError("вал M8: над головкой болта меньше 4 мм пластика колонны")
    holes = [cyl(M8["hole"] / 2.0, z_hb - 0.1, col_top + 1, S.x, S.y),
             hexagon(M8_HEAD_S + 0.3, top - 1, z_hb, S.x, S.y, 90.0)]
    col = rounded_rect(S.x - col_f, S.x + col_f, S.y - col_f, S.y + col_f, top, top + foot_t, 4.0)
    col = col.fuse(cyl(col_r, top, col_top, S.x, S.y))
    col = col.cut(holes + [cyl(INSERT_D / 2.0, top - 1, top + INSERT_L + 0.5, x, y) for x, y in col_ins])
    feat(doc, part, "FR_Column", "Стойка_вала_печать", col.removeSplitter(), PLA)

    # фанера: отверстия под потайные винты (зенковка снизу)
    csk_pts = col_ins + [(p.x, p.y) for p, _, _, _, _, _ in stands]
    pcuts = []
    for x, y in csk_pts:
        pcuts += [cyl(M3["hole"] / 2.0, fl - 1, top + 1, x, y),
                  cyl(CSK_DK / 2.0 + 0.2, fl - 1, fl + CSK_SINK, x, y),
                  Part.makeCone(CSK_DK / 2.0 + 0.2, M3["hole"] / 2.0, CSK_K, V(x, y, fl + CSK_SINK))]
    base = soften(base, 1.5, (top,), "основание").cut(pcuts).removeSplitter()
    feat(doc, part, "FR_Base", "Основание_фанера_6мм", base, PLY)
    down = App.Rotation(V(1, 0, 0), 180)
    for i, (x, y) in enumerate(col_ins):
        o = feat(doc, part, "FR_BaseIns%d" % (i + 1), "Вставка_резьбовая_M3x5_осн_%d" % (i + 1),
                 tube(INSERT_D / 2.0, 1.5, 0, INSERT_L), (0.80, 0.62, 0.20))
        o.Placement.Base = V(x, y, top)
        o = feat(doc, part, "FR_BaseScr%d" % (i + 1), "Винт_осн_M3x%d_ISO10642_%d" % (CSK_L, i + 1),
                 csk_screw(M3, CSK_L), DARK)
        o.Placement = App.Placement(V(x, y, fl + CSK_SINK), down)

    # стойки, шайбы, винты снизу и сверху
    k = len(col_ins)
    for i, (p, L, nw, u, z0p, t) in enumerate(stands):
        tag = "%s%d" % ("A" if z0p == zA0 else "B", i + 1 if z0p == zA0 else i + 1 - len(stA))
        zs = top + nw * WASH_S                              # низ стойки
        for j in range(nw):
            o = feat(doc, part, "FR_StdWash%s_%d" % (tag, j + 1), "Шайба_M3_DIN125_стойки_%s_%d" % (tag, j + 1),
                     tube(WASH_D / 2.0, 1.6, 0, WASH_S), STEEL)
            o.Placement.Base = V(p.x, p.y, top + j * WASH_S)
        sh = hexagon(STD_S, zs, zs + L, p.x, p.y, 90.0).cut(cyl(STD_BORE / 2.0, zs - 1, zs + L + 1, p.x, p.y))
        feat(doc, part, "FR_Std%s" % tag, "Стойка_латунь_M3x%d_ВВ_плита_%s" % (L, tag), sh, BRASS)
        k += 1
        Lb = screw_len(e.BaseT.Value - CSK_SINK + nw * WASH_S + STD_THREAD)
        o = feat(doc, part, "FR_BaseScr%d" % k, "Винт_осн_M3x%d_ISO10642_стойка_%s" % (Lb, tag),
                 csk_screw(M3, Lb), DARK)
        o.Placement = App.Placement(V(p.x, p.y, fl + CSK_SINK), down)
        Lt = screw_len(t + STD_THREAD)
        o = feat(doc, part, "FR_PlScr%s" % tag, "Винт_плиты_M3x%d_ISO7380_%s" % (Lt, tag),
                 button_screw(M3, Lt), DARK)
        o.Placement.Base = V(p.x, p.y, z0p + t)

    # --- плиты моторов — фанера 6 мм. Мотор центрируется буртиком Ø22 в
    #     сквозном отверстии Ø23 (в него же входит ступица шкива 1).
    #     НАТЯЖЕНИЕ РЕМНЯ — сдвигом всей плиты с мотором вдоль ремня: пазы
    #     ±TensionSlot под винтами плиты к стойкам (их крутят сверху).
    #     Винты мотора к плите — простые отверстия: мотор крепят на столе
    #     до ремня. Под ближним к центру винтом мотора проходит ветвь
    #     ремня, на собранном роботе к нему не подлезть — поэтому
    #     натягивать сдвигом мотора по плите нельзя.
    def motor_plate(outline, z0, z1, M, u, pts, name):
        cuts = [cyl((NEMA_BOSS + 1.0) / 2.0, z0 - 1, z1 + 1, M.x, M.y)]
        for sx in (-1, 1):
            for sy in (-1, 1):
                cuts.append(cyl(M3["hole"] / 2.0, z0 - 1, z1 + 1,
                                M.x + sx * NEMA_PCD / 2, M.y + sy * NEMA_PCD / 2))
        for p in pts:
            cuts.append(slot(M3["hole"] / 2.0, z0 - 1, z1 + 1, p, u, slot_h))
        return soften(outline, 1.0, (z1,), name).cut(cuts)

    plA = rounded_rect(-37.5, NEMA_HALF + 5.0, -37.5, ymid - 0.5, zA0, zA1, 4.0)
    plA = plA.cut(cyl(rod_keep, zA0 - 1, zA1 + 1, S.x, S.y))
    feat(doc, part, "FR_PlateA", "Плита_мотора_1_фанера_6мм",
         motor_plate(plA, zA0, zA1, M1, u1, stA, "плита 1"), PLY)
    plB = rounded_rect(-28.0, 48.0, ymid + 0.5, 80.0, zB0, zB1, 4.0)
    plB = plB.cut(cyl(rod_keep, zB0 - 1, zB1 + 1, S.x, S.y))
    # плита 2 — на высоте верха трубы плеча, и на парковке (плечо 136 ± 2°)
    # труба проходит под её передним углом: срезать всё ближе PARK_KEEP к
    # оси трубы при плече PARK_T1_MAX
    park = box(-50.0, 400.0, -400.0, PARK_KEEP, zB0 - 1, zB1 + 1)
    park.rotate(V(0, 0, 0), V(0, 0, 1), PARK_T1_MAX)
    park.translate(S)
    plB = plB.cut(park)
    feat(doc, part, "FR_PlateB", "Плита_мотора_2_фанера_6мм",
         motor_plate(plB, zB0, zB1, M2, u2, stB, "плита 2"), PLY)

    # винты моторов: мотор 1 — СНИЗУ сквозь плиту в резьбу фланца (головка
    # под плитой), мотор 2 висит под плитой — винты СВЕРХУ
    for tag, M, zseat, t, rot, shp in (("A", M1, zA0, tA, down, cap_screw),
                                       ("B", M2, zB1, tB, App.Rotation(), button_screw)):
        L = screw_len(t + 4.0)
        for k, (sx, sy) in enumerate(((-1, -1), (-1, 1), (1, -1), (1, 1))):
            o = feat(doc, part, "FR_MotScr%s%d" % (tag, k + 1),
                     "Винт_мотора_%s_M3x%d_%s_%d" % ("1" if tag == "A" else "2", L,
                                                    "ISO4762" if tag == "A" else "ISO7380", k + 1),
                     shp(M3, L), DARK)
            o.Placement = App.Placement(V(M.x + sx * NEMA_PCD / 2, M.y + sy * NEMA_PCD / 2, zseat), rot)

    # --- вал: болт M8 снизу, втулки по внутренним кольцам, шайба и гайка сверху ---
    feat(doc, part, "FR_ShaftBushLo", "Втулка_вала_нижняя_Ø12/Ø8.2x%.1f" % bush_lo,
         tube(6.0, 4.1, col_top, Z0, S.x, S.y), STEEL)
    zt = Z0 + d.BrgZ2.Value + d.BrgW2.Value
    feat(doc, part, "FR_ShaftBushHi", "Втулка_вала_верхняя_Ø12/Ø8.2x4",
         tube(6.0, 4.1, zt, zt + 4.0, S.x, S.y), STEEL)
    o = feat(doc, part, "FR_ShaftBolt", "Болт_вала_M8x%d_DIN931" % bolt_L, hex_bolt(M8, bolt_L), DARK)
    o.Placement.Base = V(S.x, S.y, z_hb)
    feat(doc, part, "FR_ShaftWash", "Шайба_вала_M8_DIN125",
         tube(WASH8_D / 2.0, 4.2, zt + 4.0, zt + 4.0 + WASH8_S, S.x, S.y), STEEL)
    o = feat(doc, part, "FR_ShaftNut", "Гайка_вала_M8_ISO4032", nut(M8, 90.0), STEEL)
    o.Placement.Base = V(S.x, S.y, z_nt - M8["nut_m"])

    # --- ремни GT2: огибающая по делительным окружностям ---
    def belt(c1, r1, c2, r2, z0, w):
        def hull(dr):
            a = Part.makeCircle(r1 + dr, V(c1.x, c1.y, z0))
            b = Part.makeCircle(r2 + dr, V(c2.x, c2.y, z0))
            # внешние касательные двух окружностей
            dv = c2 - c1
            L = dv.Length
            ang = math.atan2(dv.y, dv.x)
            phi = math.acos(((r1 + dr) - (r2 + dr)) / L)
            pts = []
            n = 48
            for k in range(n + 1):     # дуга на c1
                t = ang + phi + (2 * math.pi - 2 * phi) * k / n
                pts.append(V(c1.x + (r1 + dr) * math.cos(t), c1.y + (r1 + dr) * math.sin(t), z0))
            for k in range(n + 1):     # дуга на c2
                t = ang - phi + 2 * phi * k / n
                pts.append(V(c2.x + (r2 + dr) * math.cos(t), c2.y + (r2 + dr) * math.sin(t), z0))
            pts.append(pts[0])
            return Part.Face(Part.makePolygon(pts)).extrude(V(0, 0, w))
        return hull(0.75).cut(hull(-0.63))
    pd1 = d.PitchD1.Value / 2.0
    zr1 = d.BeltPlaneZ.Value + (d.RimH.Value - d.BeltWidth.Value) / 2.0
    feat(doc, part, "FR_Belt1", "Ремень_GT2-%.0f_ступень_1" % d.BeltLength.Value,
         belt(S, d.PitchD2.Value / 2.0, M1, pd1, zr1, d.BeltWidth.Value), BELT)
    zr2 = Z0 + d.BeltPlaneZ2.Value + (d.RimH2.Value - d.BeltWidth2.Value) / 2.0
    feat(doc, part, "FR_Belt2", "Ремень_GT2-%.0f_ступень_2" % d.BeltLength2.Value,
         belt(S, d.PitchDriven2.Value / 2.0, M2, d.PitchDriver2.Value / 2.0, zr2,
              d.BeltWidth2.Value), BELT)
    doc.recompute()
    return part


# ---------------------------------------------------------------------------
# Рабочий узел
# ---------------------------------------------------------------------------
def build_effector(doc, d, e):
    purge(doc, ("EF_", "CR_"))
    tube_part = doc.getObject("Part_Tube")
    eff = container(doc, EFF_PART, "Рабочий_узел", tube_part)
    carr = container(doc, CARR_PART, "Каретка_Z", eff)
    eff.setExpression("Placement.Base.x", "%s.PivotX" % VS)
    eff.setExpression("Placement.Rotation.Angle", "Poza.Tube2Angle")       # поза — в своём VarSet, см. shkiv_param
    # грань магнита: высота над полем -> z в Part_Tube
    carr.setExpression("Placement.Base.z", "%s.FloorZ + %s.MagnetZ - (%s.BeltPlaneZ - %s.FlangeThk)"
                       % (VE, VE, VS, VS))

    tz = d.Tube2Z.Value               # ось трубы 2 во фрейме предплечья
    r_t = d.TubeOD.Value / 2.0
    hw = d.ElbowHalfW.Value
    bot = d.ElbowBot.Value
    capt = d.CapThk.Value
    sy = d.ElbowScrewY.Value
    zf_low = e.FloorZ.Value + 4.0 - (d.BeltPlaneZ.Value - d.FlangeThk.Value)   # грань магнита внизу
    # рельс: каретка MGN9H ходит от (магнит внизу) до (магнит вверху);
    # 100-мм рельс ставится по центру этого хода
    blk_lo = zf_low + BLK_ZC - BLK_L / 2.0
    blk_hi = zf_low + Z_STROKE + BLK_ZC + BLK_L / 2.0
    rz0 = (blk_lo + blk_hi) / 2.0 - RAIL_L / 2.0
    rz1 = rz0 + RAIL_L
    rail_z0 = min(zf_low + SP_Z0, rz0)                                     # низ пластины
    # высота оси шестерни Z: рейка в зацеплении на всём ходу (по 4 мм запаса)
    zp_lo = zf_low + Z_STROKE + SP_Z0 + 4.0
    zp_hi = zf_low + SP_Z1 - 4.0
    zp = (zp_lo + zp_hi) / 2.0
    r_zp = GEAR_M * ZP_TEETH / 2.0
    y_pitch = SP_HW + 2.0                      # делительная прямая рейки
    y_zp = y_pitch + r_zp                      # ось шестерни Z / SG90 №1

    # --- кронштейн: хомут на трубе 2 + пластина направляющей + фланец серво ---
    # рельс по высоте: снизу — где ползун при магните на поле, сверху — где
    # он при магните вверху. От высоты руки это не зависит: рука может
    # стоять низко, а каретка всё равно ходит от поля +4 до +38.6
    rail_z1 = max(tz + capt, rz1)
    clamp = box(CL_X0, GP_X1, -hw, hw, tz - bot, tz)
    plate = box(GP_X0, GP_X1, -GP_HW, GP_HW, rail_z0, rail_z1)
    ribs = []
    if rail_z0 + 8 < tz - bot:      # пластина ниже хомута: косынка снизу по оси
        ribs.append(Part.Face(Part.makePolygon(
            [V(CL_X0 + 6, -2, tz - bot), V(GP_X0, -2, tz - bot),
             V(GP_X0, -2, rail_z0 + 8), V(CL_X0 + 6, -2, tz - bot)])).extrude(V(0, 4, 0)))
    # боковые косынки за пластиной на всю её высоту — снаружи хомута (|y| > hw),
    # мимо винтов крышки и SG90 №1
    for y0 in (GP_HW - 4.0, -GP_HW):
        ribs.append(Part.Face(Part.makePolygon(
            [V(GP_X0 - 10, y0, tz - bot), V(GP_X0, y0, rail_z0 + 4), V(GP_X0, y0, rail_z1 - 4),
             V(GP_X0 - 10, y0, tz + capt), V(GP_X0 - 10, y0, tz - bot)])).extrude(V(0, 4, 0)))
    rib = ribs[0].fuse(ribs[1:]) if len(ribs) > 1 else ribs[0]
    # фланец SG90 №1: лапки ложатся на его заднюю грань x = SERVO_FLANGE_X
    sv_z0 = zp - SG_AXIS_Y                     # где у серво y_s = 0
    fl_y0, fl_y1 = GP_HW - 1.0, y_zp + 5.9 + 3.0
    fl_z0, fl_z1 = sv_z0 - 4.7 - 1.5, sv_z0 + 27.7 + 1.5
    # фланец вынесен вперёд пластины (шестерня Z должна попасть на рейку
    # каретки, а та теперь стоит на MGN9H); за его передней стенкой —
    # карман под лапки, сзади открыт: туда заходит отвёртка
    flange = box(GP_X0, SERVO_FLANGE_X + 4.0, fl_y0, fl_y1, fl_z0, fl_z1)
    win = box(GP_X0 - 1, SERVO_FLANGE_X + 5.0, y_zp - 5.9 - 0.3, y_zp + 5.9 + 0.3,
              sv_z0 - 0.3, sv_z0 + 22.5 + 0.3)
    tabs = box(GP_X0 - 1, SERVO_FLANGE_X, y_zp - 6.2, y_zp + 6.2, sv_z0 - 5.5, sv_z0 + 28.5)
    br = clamp.fuse([plate, rib, flange.cut(win).cut(tabs)]).removeSplitter()
    cuts = [cyl_x(r_t, CL_X0 - 1, GP_X0, 0, tz)]
    for xs in CL_SCREW_X:
        for s_ in (1, -1):
            cuts.append(cyl(M3["hole"] / 2.0, tz - bot - 1, tz + 1, xs, s_ * sy))
            cuts.append(nut_pocket(M3, tz - bot, xs, s_ * sy, V(0, s_, 0), rot=0.0, depth=12))
    for ys in SG_HOLES_Y:       # отверстия под саморезы M2 лапок SG90 №1 (Ø1.6)
        cuts.append(cyl_x(0.8, SERVO_FLANGE_X - 1, SERVO_FLANGE_X + 5, y_zp, sv_z0 + ys))
    rail_holes = [rz0 + RAIL_E + RAIL_P * i for i in range(int((RAIL_L - 2 * RAIL_E) / RAIL_P) + 1)]
    for zh_ in rail_holes:      # гнёзда резьбовых вставок M3 под винты рельса
        cuts.append(cyl_x(INSERT_D / 2.0, RAIL_X0 - INSERT_L, RAIL_X0 + 0.1, 0, zh_))
    br = br.cut(cuts)
    feat(doc, eff, "EF_Bracket", "Кронштейн_Z", br, PLA2)

    # --- рельс MGN9 100 мм на пластине: 5 винтов M3x8 во вставки ---
    rl = box(RAIL_X0, RAIL_X0 + RAIL_H, -RAIL_W / 2.0, RAIL_W / 2.0, rz0, rz1)
    for zh_ in rail_holes:
        rl = rl.cut(cyl_x(RAIL_HOLE / 2.0, RAIL_X0 - 1, RAIL_X0 + RAIL_H + 1, 0, zh_))
        rl = rl.cut(cyl_x(RAIL_CB_D / 2.0, RAIL_X0 + RAIL_H - RAIL_CB_H, RAIL_X0 + RAIL_H + 1, 0, zh_))
    feat(doc, eff, "EF_Rail", "Рельс_MGN9_100мм", rl, STEEL)
    to_x = App.Rotation(V(0, 1, 0), 90)       # ось винта Z -> +X (головкой наружу)
    for i, zh_ in enumerate(rail_holes):
        feat(doc, eff, "EF_Insert%d" % (i + 1), "Вставка_резьбовая_M3x5_%d" % (i + 1),
             tube(INSERT_D / 2.0, 1.5, 0, INSERT_L), (0.80, 0.62, 0.20)).Placement = \
            App.Placement(V(RAIL_X0 - INSERT_L, 0, zh_), to_x)
        o = feat(doc, eff, "EF_RailScr%d" % (i + 1), "Винт_рельса_M3x8_%d" % (i + 1),
                 cap_screw(M3, 8), DARK)
        o.Placement = App.Placement(V(RAIL_X0 + RAIL_H - RAIL_CB_H, 0, zh_), to_x)
    capb = box(CL_X0, GP_X0, -hw, hw, tz, tz + capt).cut(cyl_x(r_t, CL_X0 - 1, GP_X0 + 1, 0, tz))
    for xs in CL_SCREW_X:
        for s_ in (1, -1):
            capb = capb.cut(cyl(M3["hole"] / 2.0, tz - 1, tz + capt + 1, xs, s_ * sy))
            capb = capb.cut(cyl(M3["dk"] / 2.0 + 0.25, tz + capt - d.CapWall.Value, tz + capt + 1,
                                xs, s_ * sy))
    feat(doc, eff, "EF_BracketCap", "Кронштейн_Z_крышка", capb, PLA2)
    k = 0
    for xs in CL_SCREW_X:
        for s_ in (1, -1):
            k += 1
            o = feat(doc, eff, "EF_ClScr%d" % k, "Винт_кронштейна_M3x16_%d" % k, cap_screw(M3, 16), DARK)
            o.Placement.Base = V(xs, s_ * sy, tz + capt - d.CapWall.Value)
            o = feat(doc, eff, "EF_ClNut%d" % k, "Гайка_кронштейна_M3_%d" % k, nut(M3, 0.0), STEEL)
            o.Placement.Base = V(xs, s_ * sy, tz - bot + 0.2)

    # --- SG90 №1: ось выхода вдоль +X, лапки на фланце ---
    s1 = sg90()
    # серво: z_s -> +X (лапки z_s 18.4 на x = SERVO_FLANGE_X), y_s -> +Z
    pl = App.Placement(V(SERVO_FLANGE_X - SG_TAB_Z1, y_zp, sv_z0),
                       App.Rotation(V(0, 1, 0), V(0, 0, 1), V(1, 0, 0), "ZXY"))
    o = feat(doc, eff, "EF_ServoZ", "Серво_Z_SG90", s1, SERVO)
    o.Placement = pl
    gx0 = SERVO_FLANGE_X - SG_TAB_Z1 + SG_GEAR_Z
    # шестерня Z: ось по X, при угле 0 зуб смотрит на рейку (-Y). Угол
    # поворота привязан к высоте магнита — шестерня катится по рейке, и
    # зубья в модели всегда в зацеплении, а не друг в друге.
    gz = involute_gear(GEAR_M, ZP_TEETH, GEAR_W, bore=4.9, plane="yz", phase=180.0)
    o = feat(doc, eff, "EF_GearZ", "Шестерня_Z_m1_z%d" % ZP_TEETH, gz, (0.95, 0.95, 0.95))
    o.Placement = App.Placement(V(gx0, y_zp, zp), App.Rotation(V(1, 0, 0), 0.001))
    z0f = d.BeltPlaneZ.Value - d.FlangeThk.Value
    o.setExpression("Placement.Rotation.Angle",
                    "(%.4f mm - %s.FloorZ - %s.MagnetZ) / %.4f mm * 180 deg / pi"
                    % (zp - SP_Z0 + z0f, VE, VE, r_zp))
    for j, ys in enumerate(SG_HOLES_Y):
        sc = cyl(1.0, -6.0, 0.0).fuse(cyl(2.0, 0.0, 1.4))      # саморез 2x6 из комплекта SG90
        sc.Placement = App.Placement(V(SERVO_FLANGE_X - SG_TAB_Z1 + SG_TAB_Z0, y_zp, sv_z0 + ys),
                                     App.Rotation(V(0, 1, 0), -90))
        feat(doc, eff, "EF_SvScrZ%d" % (j + 1), "Саморез_SG90_2x6_Z_%d" % (j + 1), sc, DARK)

    # --- каретка (всё дальше — в координатах «грань магнита = z 0») ---
    xs_ = SPINDLE_X
    spine = box(SP_X0, SP_X1, -SP_HW, SP_HW, SP_Z0, SP_TOP)
    # рейка на +Y грани ползуна, ширина по X = под шестерню Z с запасом
    rk = rack(GEAR_M, SP_Z1 - SP_Z0, GEAR_W + 1.0, SP_Z0, 2.0)
    rk.translate(V(gx0 - 0.5, y_pitch, 0))
    hous = cyl(HOUS_R, HOUS_Z0, HOUS_Z1, xs_, 0)
    web = box(SP_X1 - 1, xs_, -10.0, 10.0, HOUS_Z0, HOUS_Z1)
    # SG90 №2: ось на (xs, -a), корпус вдоль +X, лапки на приливах
    a_w = GEAR_M * (SPG_TEETH + RTP_TEETH) / 2.0              # межосевое 19.5
    rt_y = -a_w
    sv2_z0 = HOUS_Z1 + 1.0 - SG_GEAR_Z                        # шестерня 2 на уровне шестерни шпинделя
    tab_z = sv2_z0 + SG_TAB_Z0
    # x вдоль корпуса: x = xs + (16.6 - y_s)
    xs_of = lambda ys: xs_ + (SG_AXIS_Y - ys)
    lug1 = box(xs_of(27.7) - 0.5, xs_of(22.5) + 0.0, rt_y - 5.9 - 0.5, -9.0, tab_z - 5.0, tab_z)
    lug2 = box(xs_of(0.0), xs_of(-4.7) + 0.5, rt_y - 5.9 - 0.5, rt_y + 5.9 + 0.5, tab_z - 5.0, tab_z)
    arm2 = box(xs_ + 4.0, xs_of(-4.7) + 0.5, rt_y + 5.9 + 0.3, -6.0, tab_z - 5.0, tab_z)
    web2 = box(SP_X1 - 1, xs_of(22.5), rt_y - 5.9 - 0.5, -9.0, HOUS_Z0, tab_z)
    car = spine.fuse([rk, hous, web, lug1, lug2, arm2, web2]).removeSplitter()
    blk_holes = [(sy_ * BLK_B / 2.0, BLK_ZC + sz_ * BLK_C / 2.0) for sy_ in (-1, 1) for sz_ in (-1, 1)]
    for yy, zz in blk_holes:    # винты каретки MGN9H — спереди сквозь плиту
        car = car.cut(cyl_x(M3["hole"] / 2.0, SP_X0 - 1, SP_X1 + 1, yy, zz))
    # гнёзда 625ZZ снизу и сверху, просвет между ними
    car = car.cut([cyl(BRG625["D"] / 2.0, HOUS_Z0 - 1, HOUS_Z0 + BRG625["B"], xs_, 0),
                   cyl(BRG625["D"] / 2.0, HOUS_Z1 - BRG625["B"], HOUS_Z1 + 1, xs_, 0),
                   cyl(BRG625["d1"] / 2.0 + 0.5, HOUS_Z0, HOUS_Z1, xs_, 0)])
    for ys in SG_HOLES_Y:
        car = car.cut(cyl(0.8, tab_z - 6, tab_z + 1, xs_of(ys), rt_y))
    feat(doc, carr, "CR_Carriage", "Каретка_Z_плита_шпиндель", car, PLA2)

    # каретка MGN9H: стальной корпус с каналом под рельс (шарики не моделируем)
    blk = box(RAIL_X0 + BLK_H1, BLK_FACE, -BLK_W / 2.0, BLK_W / 2.0,
              BLK_ZC - BLK_L / 2.0, BLK_ZC + BLK_L / 2.0)
    blk = blk.cut(box(RAIL_X0 - 1, RAIL_X0 + RAIL_H + 0.3, -RAIL_W / 2.0 - 0.3, RAIL_W / 2.0 + 0.3,
                      BLK_ZC - BLK_L, BLK_ZC + BLK_L))
    for yy, zz in blk_holes:
        blk = blk.cut(cyl_x(1.5, BLK_FACE - 3.0, BLK_FACE + 1, yy, zz))
    feat(doc, carr, "CR_Block", "Каретка_MGN9H", blk, STEEL)
    for k, (yy, zz) in enumerate(blk_holes):
        o = feat(doc, carr, "CR_BlkScr%d" % (k + 1), "Винт_каретки_M3x8_%d" % (k + 1),
                 cap_screw(M3, 8), DARK)
        o.Placement = App.Placement(V(SP_X1, yy, zz), App.Rotation(V(0, 1, 0), 90))

    # подшипники и стопка внутренних колец шпинделя
    for nm, z0 in (("CR_Brg1", HOUS_Z0), ("CR_Brg2", HOUS_Z1 - BRG625["B"])):
        feat(doc, carr, nm, "Подшипник_шпинделя_625ZZ_%s" % nm[-1],
             tube(BRG625["D"] / 2.0, BRG625["d"] / 2.0, z0, z0 + BRG625["B"], xs_, 0), STEEL)
    feat(doc, carr, "CR_InnerSp", "Втулка_шпинделя_Ø7/Ø5.2x%.0f" % (HOUS_Z1 - HOUS_Z0 - 2 * BRG625["B"]),
         tube(3.5, 2.6, HOUS_Z0 + BRG625["B"], HOUS_Z1 - BRG625["B"], xs_, 0), STEEL)
    feat(doc, carr, "CR_Ext", "Удлинитель_шпинделя_Ø7/Ø5.2x%.0f" % EXT_H,
         tube(3.5, 2.6, HOLD_Z1, HOLD_Z1 + EXT_H, xs_, 0), STEEL)
    # --- вакуумный захват: держатель + присоска на оси шпинделя (рабочая грань z 0 = губа) ---
    hold = cyl(HOLD_R, HOLD_Z0, HOLD_Z1, xs_, 0)
    barb = Part.makeCylinder(1.9, BARB_R1 - 2.0 - (HOLD_R - 0.5), V(0, 0, 0), V(1, 0, 0))
    barb.translate(V(HOLD_R - 0.5, 0, 0))
    barb = barb.fuse(Part.makeCone(2.25, 1.7, 2.0, V(BARB_R1 - 2.0, 0, 0), V(1, 0, 0)))
    barb.rotate(V(0, 0, 0), V(0, 0, 1), BARB_A)
    barb.translate(V(xs_, 0, CH_Z))
    hold = hold.fuse(barb)
    zz = HOLD_Z0
    for i, (dd, hh) in enumerate(CUP_SOCK):              # нахлёст 0.01 — только шейке в диск
        hold = hold.fuse(cyl(dd / 2.0, zz - hh, zz + (0.01 if i == 0 else 0.0), xs_, 0))
        zz -= hh
    # грибок: шейка Ø4.2 (вход гнезда), головка Ø6.8 (расширение) — на её
    # торце заходная фаска, плоский уступ сверху держит присоску
    hold = hold.cut(cyl(CUP_SOCK[1][0] / 2.0 + 1, zz - 1, zz + HEAD_CH, xs_, 0).cut(
        Part.makeCone(CUP_SOCK[1][0] / 2.0 - HEAD_CH, CUP_SOCK[1][0] / 2.0, HEAD_CH, V(xs_, 0, zz))))
    hold = hold.removeSplitter()
    hcut = [cyl(NIP_BORE, HOLD_Z0 - 9.0, CH_Z, xs_, 0)]     # канал штуцера вверх до поперечного
    bb_ = Part.makeCylinder(0.9, BARB_R1 + 1.0, V(0, 0, 0), V(1, 0, 0))
    bb_.rotate(V(0, 0, 0), V(0, 0, 1), BARB_A)
    bb_.translate(V(xs_, 0, CH_Z))
    hcut.append(bb_)
    # винт шпинделя M5 — в гайку внутри держателя (паз гнезда наружу, на +Y, мимо штуцера);
    # глухое отверстие кончается в 1 мм над каналом — вакуум к винту не уходит
    zs5 = CH_Z + 0.9 + 1.0
    zn5 = zs5 + 1.0
    hcut.append(cyl(M5["hole"] / 2.0, zs5, HOLD_Z1 + 1, xs_, 0))
    hcut.append(nut_pocket(M5, zn5, xs_, 0, V(0, 1, 0), rot=0.0, depth=20))
    hold = hold.cut(hcut).removeSplitter()
    feat(doc, carr, "CR_CupHolder", "Держатель_присоски_печать", hold, PLA2)
    o = feat(doc, carr, "CR_HolderNut", "Гайка_держателя_M5", nut(M5, 0.0), STEEL)
    o.Placement.Base = V(xs_, 0, zn5 + 0.2)
    # присоска DP8: тело вращения по чертежу (r, z), губа на z 0
    outer = [(3.3, 0.0), (CUP_LIP_R, 0.0), (CUP_LIP_R, 0.5), (2.6, 2.6), (5.0, 5.2), (3.4, 7.6),
             (5.6, 10.0), (CUP_TOP_R, 11.0), (CUP_TOP_R, CUP_H - 0.8), (CUP_TOP_R - 0.8, CUP_H)]
    inner = [(CUP_SOCK[0][0] / 2.0, CUP_H), (CUP_SOCK[0][0] / 2.0, CUP_H - CUP_SOCK[0][1]),
             (CUP_SOCK[1][0] / 2.0, CUP_H - CUP_SOCK[0][1]),
             (CUP_SOCK[1][0] / 2.0, CUP_H - CUP_SOCK[0][1] - CUP_SOCK[1][1]),
             (2.6, 7.6), (4.1, 5.2), (1.0, 2.8), (1.0, 2.4)]
    prof = [V(r, 0, z) for r, z in outer + inner] + [V(outer[0][0], 0, outer[0][1])]
    cup = Part.Face(Part.makePolygon(prof)).revolve(V(0, 0, 0), V(0, 0, 1), 360)
    o = feat(doc, carr, "CR_Cup1", "Присоска_DP8", cup, (0.12, 0.12, 0.12))
    o.Placement.Base = V(xs_, 0, 0)
    g_sp = involute_gear(GEAR_M, SPG_TEETH, GEAR_W, bore=5.3, shift=SPG_SHIFT, z0=HOUS_Z1 + 1.0)
    g_sp = g_sp.fuse(tube(3.5, 2.65, HOUS_Z1, HOUS_Z1 + 1.0)).removeSplitter()   # бобышка по внутр. кольцу
    g_sp.translate(V(xs_, 0, 0))
    feat(doc, carr, "CR_GearSp", "Шестерня_шпинделя_m1_z%d" % SPG_TEETH, g_sp, (0.95, 0.95, 0.95))
    zh = HOUS_Z1 + 1.0 + GEAR_W
    L4 = int(math.ceil(zh - zn5 + 0.5))                     # проходит гайку держателя насквозь
    o = feat(doc, carr, "CR_Screw", "Винт_шпинделя_M5x%.0f_ISO4762" % L4, cap_screw(M5, L4), DARK)
    o.Placement.Base = V(xs_, 0, zh)
    s2 = sg90()
    o = feat(doc, carr, "CR_ServoR", "Серво_поворота_SG90", s2, SERVO)
    # y_s -> -X (корпус уходит вперёд), x_s -> Y, z_s -> Z
    o.Placement = App.Placement(V(xs_ + SG_AXIS_Y, rt_y, sv2_z0),
                                App.Rotation(V(0, 0, 1), 90))
    g_rt = involute_gear(GEAR_M, RTP_TEETH, GEAR_W, bore=4.9, shift=RTP_SHIFT, z0=HOUS_Z1 + 1.0)
    g_rt.rotate(V(0, 0, 0), V(0, 0, 1), 90.0 % (360.0 / RTP_TEETH))   # зуб к шпинделю
    g_rt.translate(V(xs_, rt_y, 0))
    feat(doc, carr, "CR_GearRt", "Шестерня_поворота_m1_z%d" % RTP_TEETH, g_rt, (0.95, 0.95, 0.95))
    for j, ys in enumerate(SG_HOLES_Y):
        sc = cyl(1.0, -6.0, 0.0).fuse(cyl(2.0, 0.0, 1.4))
        sc.translate(V(xs_of(ys), rt_y, tab_z + 2.5))
        feat(doc, carr, "CR_SvScr%d" % (j + 1), "Саморез_SG90_2x6_пов_%d" % (j + 1), sc, DARK)
    doc.recompute()
    return eff, carr, dict(zp=zp, y_zp=y_zp, zf_low=zf_low, rail_z0=rail_z0)


# ---------------------------------------------------------------------------
# Полигон-ссылка (по ETZ_poligon.FCMacro и п. 2.1-2.2 ЕТЗ)
# ---------------------------------------------------------------------------
def build_camera(doc, d, e):
    """Камера на откидной консоли (ЕТЗ п. 3.1: до старта и после финиша над
    полем ничего быть не может, поэтому неподвижно висеть над полем она не
    может). Мачта стоит НА ОСИ ШКИВОВ — на пробке, навинченной на болт вала:
    всё подвижное руки вращается вокруг этой оси и к ней не подходит, а
    консоль до центра листа вдвое короче, чем из угла фанеры. Голова зажата
    на мачте разрезным хомутом, ось консоли вынесена вбок от мачты на
    CAM_OFF: мачта проходит голову насквозь, поэтому голову можно поставить
    на любую высоту, а мачта — любой длины. На оси — ступица на двух 625ZZ,
    её поворачивает SG90 через z13 -> z26. Консоль лежит в хомуте НАД
    верхним подшипником и проходит его насквозь — её можно выдвинуть на
    любую длину. В работе консоль стоит на CamWork (камера над центром
    листа, объективом вниз) и не двигается; сложенная (CamStow) — целиком
    над зоной 1."""
    purge(doc, ("CAM_",))
    part = container(doc, "Part_Cam", "Камера")
    boom_p = container(doc, "Part_CamBoom", "Камера_консоль", part)

    P = V(d.PulleyAxisX.Value, d.ArmAxisY.Value, 0)      # ось мачты = ось шкивов
    F = poly_to_robot(d, e, SHEET_C[0], SHEET_C[1])
    stow = e.CamStow.Value
    # ось консоли A — сбоку от мачты, перпендикулярно середине сектора
    # поворота: тогда ни консоль, ни хомут ступицы над мачтой не проходят,
    # как бы высоко она ни торчала. A зависит от угла в работе, а он от A —
    # несколько итераций
    A = P
    for _ in range(6):
        vF = F - A
        work = math.degrees(math.atan2(vF.y, vF.x))
        psi = math.radians((stow + work) / 2.0 - 90.0)
        A = P + V(CAM_OFF * math.cos(psi), CAM_OFF * math.sin(psi), 0)
    vF = F - A
    reach = math.hypot(vF.x, vF.y)                       # от оси консоли до центра листа
    work = math.degrees(math.atan2(vF.y, vF.x))
    e.CamWork = work
    fl = e.FloorZ.Value
    B5 = BRG625
    rm = MAST_D / 2.0

    # --- высоты (z робота) от высоты объектива ---
    # объектив: низ ствола на 33.6 ниже оси консоли (кронштейн 9, плита 3,
    # бобышки 5, плата 1.6, объектив 15)
    zb = fl + e.CamLensH.Value + 33.6                    # ось консоли
    # над осью M5: подшипники 2 x 5 с шагом 13, шайба 1, головка M5 5, зазор 1
    Hb = zb - BOOM_D / 2.0 - 1.0 - B5["d"] - 1.0 - 13.0 - B5["B"]   # низ ступицы
    zp0 = shaft_nut_top(d)                               # низ пробки — на гайке стопки вала
    z_floor = zp0 + PLUG_FL                              # низ мачты — на фланце пробки
    z_mt = z_floor + MAST_L                              # верх мачты
    z_s1 = Hb - 0.5                                      # верх головы
    z_s0 = z_s1 - SLEEVE_H                               # низ хомута головы на мачте
    if z_mt < z_s1:
        raise RuntimeError("мачта %g коротка: голова на z %.1f, верх мачты %.1f"
                           % (MAST_L, z_s1, z_mt))
    if z_s0 < z_floor + PLUG_SPIG + 5.0:
        raise RuntimeError("голова камеры опущена до пробки мачты")

    # --- пробка мачты на конце болта вала (болт снизу, головкой в гнезде
    #     колонны, не проворачивается): во фланце снизу запрессована гайка
    #     M8 — пробку навинчивают на болт и контрят о гайку стопки
    #     (резьбу — фиксатором средней прочности); хвостовик входит в
    #     трубу мачты, мачта на поперечном винте M3. Ухо с пазом под
    #     стяжку — к моторам: кабель камеры уходит назад над шкивами ---
    zc_p = z_floor + PLUG_SPIG / 2.0                     # поперечный винт мачты
    bolt = doc.getObject("FR_ShaftBolt")
    tip = bolt.Shape.BoundBox.ZMax
    plug = cyl(PLUG_R, zp0, z_floor).fuse(cyl(rm - MAST_T - 0.15, z_floor - 0.1, z_floor + PLUG_SPIG))
    a_back = math.degrees(math.atan2(-d.ArmAxisY.Value, -d.PulleyAxisX.Value))   # на левый мотор
    ear = box(PLUG_R - 2.0, PLUG_R + 9.0, -4.0, 4.0, zp0, zp0 + 4.0).cut(
        box(PLUG_R + 3.0, PLUG_R + 6.0, -2.5, 2.5, zp0 - 1, zp0 + 5))        # паз 3 x 5 под стяжку
    ear.rotate(V(0, 0, 0), V(0, 0, 1), a_back)
    plug = plug.fuse(ear)
    plug = plug.cut([hexagon(M8["nut_s"] + 0.3, zp0 - 1, zp0 + M8["nut_m"] + 0.2, 0, 0, 90.0),
                     cyl(M8["hole"] / 2.0, zp0, tip + 1.0),
                     Part.makeCylinder(M3["hole"] / 2.0, MAST_D + 2, V(0, -rm - 1, zc_p), V(0, 1, 0))])
    plug = plug.removeSplitter()
    plug.translate(P)
    feat(doc, part, "CAM_Plug", "Пробка_мачты_печать", plug, PLA)
    o = feat(doc, part, "CAM_PlugNutM8", "Гайка_пробки_M8_ISO4032", nut(M8, 90.0), STEEL)
    o.Placement.Base = V(P.x, P.y, zp0)
    o = feat(doc, part, "CAM_PlugScr", "Винт_мачты_M3x20", cap_screw(M3, 20), DARK)
    o.Placement = App.Placement(P + V(0, rm, zc_p), App.Rotation(V(1, 0, 0), -90))
    o = feat(doc, part, "CAM_PlugNut", "Гайка_мачты_M3", nut(M3, 0.0), STEEL)
    o.Placement = App.Placement(P + V(0, -rm - M3["nut_m"] - 0.1, zc_p), App.Rotation(V(1, 0, 0), -90))

    # --- мачта: одна сверловка — под винт пробки, голова держится трением ---
    m = tube(rm, rm - MAST_T, z_floor, z_mt)
    m = m.cut(Part.makeCylinder(M3["hole"] / 2.0, 2 * rm + 2, V(0, -rm - 1, zc_p), V(0, 1, 0)))
    m.translate(P)
    feat(doc, part, "CAM_Mast", "Мачта_Al_труба_Ø%gx%g_L%g" % (MAST_D, MAST_T, MAST_L), m, STEEL)

    # --- голова: хомут на мачте + балка + бобышка оси + фланец SG90 ---
    # (своя СК: начало — ось консоли A, z — как у робота)
    phi = math.radians((stow + work) / 2.0 + 180.0)      # SG90 — напротив сектора консоли
    a_m = math.degrees(psi) + 180.0                      # направление от оси консоли к мачте
    Ml = V(CAM_OFF * math.cos(math.radians(a_m)), CAM_OFF * math.sin(math.radians(a_m)), 0)
    a_c = (CAM_GEAR_HUB + CAM_GEAR_SV) * GEAR_M / 2.0    # межосевое 21.5
    C = V(a_c * math.cos(phi), a_c * math.sin(phi), 0)
    t_ = V(-math.sin(phi), math.cos(phi), 0)
    z_sv = Hb - SG_GEAR_Z                                # z «y_s = 0» серво: шестерня на уровне ступицы
    tab0 = z_sv + SG_TAB_Z0
    sv_pl = App.Placement(C - t_ * SG_AXIS_Y + V(0, 0, z_sv), App.Rotation(V(0, 0, 1), math.degrees(phi)))
    z_h0 = Hb - 16.0                                     # низ бобышки оси
    head = cyl(13.0, z_h0, z_s1).fuse(cyl(3.75, z_s1 - 0.1, Hb))   # буртик под внутр. кольцо
    beam = box(0, CAM_OFF, -8.0, 8.0, z_h0, z_s1)        # балка к мачте
    beam.rotate(V(0, 0, 0), V(0, 0, 1), a_m)
    web = box(0, 14.0, -10.0, 10.0, z_h0, tab0)          # перемычка к фланцу SG90
    web.rotate(V(0, 0, 0), V(0, 0, 1), math.degrees(phi))
    # хомут на мачте (СК мачты: +x — наружу, от оси консоли): втулка с
    # разрезом наружу и ушами; две стяжки M3x14 поперёк разреза, головки —
    # на стороне -y, гайки утоплены в ухо +y
    ear_x1, ear_hw, ear_sx = rm + 12.0, 7.0, rm + 6.0
    z_ears = (z_s0 + 10.0, z_s1 - 10.0)
    sl = cyl(rm + 4.0, z_s0, z_s1).fuse(box(0, ear_x1, -ear_hw, ear_hw, z_s0, z_s1))
    sl_cut = [cyl(rm + 0.15, z_s0 - 1, z_s1 + 1),
              box(rm - 1.0, ear_x1 + 1, -1.0, 1.0, z_s0 - 1, z_s1 + 1)]      # разрез
    for zc in z_ears:
        sl_cut.append(Part.makeCylinder(M3["hole"] / 2.0, 2 * ear_hw + 2, V(ear_sx, -ear_hw - 1, zc),
                                        V(0, 1, 0)))
        hx = hexagon(M3["nut_s"] + 0.3, 0, M3["nut_m"] + 0.5)
        hx.rotate(V(0, 0, 0), V(1, 0, 0), -90)            # ось гайки -> +Y
        hx.translate(V(ear_sx, ear_hw - M3["nut_m"] - 0.45, zc))
        sl_cut.append(hx)
    sl_rot = App.Rotation(V(0, 0, 1), a_m)
    for s_ in [sl] + sl_cut:
        s_.rotate(V(0, 0, 0), V(0, 0, 1), a_m)
        s_.translate(Ml)
    # фланец SG90 (в координатах серво): лапки ложатся сверху, корпус — в окне
    fl_s = box(-9.5, 7.5, -6.5, 29.5, tab0 - 4.0, tab0)
    fl_s = fl_s.cut(box(-6.2, 6.2, -0.3, 22.8, tab0 - 5, tab0 + 1))
    for ys in SG_HOLES_Y:
        fl_s = fl_s.cut(cyl(0.8, tab0 - 5, tab0 + 1, 0, ys))
    fl_s.rotate(V(0, 0, 0), V(0, 0, 1), math.degrees(phi))
    fl_s.translate(V(sv_pl.Base.x, sv_pl.Base.y, 0))
    head = head.fuse([beam, web, sl, fl_s]).removeSplitter()
    head = head.cut(sl_cut)
    head = head.cut(cyl(2.65, z_h0 - 1, Hb + 1))          # ось M5
    zn = Hb - 10.5                                       # гайка M5 в гнезде бобышки
    a5 = round((math.degrees(phi) + 180.0) / 15.0) * 15.0   # паз — наружу от серво, по сетке 15°
    rot5 = a5 - 90.0                                     # грани гайки вдоль паза
    u5 = V(math.cos(math.radians(a5)), math.sin(math.radians(a5)), 0)
    head = head.cut(nut_pocket(M5, zn, 0, 0, u5, rot=rot5, depth=20))
    head = head.removeSplitter()
    head.translate(A)
    feat(doc, part, "CAM_Head", "Голова_консоли_печать", head, PLA)
    for k, zc in enumerate(z_ears):
        q = A + Ml + sl_rot.multVec(V(ear_sx, 0, 0))
        o = feat(doc, part, "CAM_HeadScr%d" % (k + 1), "Винт_хомута_головы_M3x14_%d" % (k + 1),
                 cap_screw(M3, 14), DARK)
        o.Placement = App.Placement(q + sl_rot.multVec(V(0, -ear_hw, 0)) + V(0, 0, zc),
                                    sl_rot.multiply(App.Rotation(V(1, 0, 0), 90)))
        o = feat(doc, part, "CAM_HeadNut%d" % (k + 1), "Гайка_хомута_головы_M3_%d" % (k + 1),
                 nut(M3, 0.0), STEEL)
        o.Placement = App.Placement(q + sl_rot.multVec(V(0, ear_hw - M3["nut_m"] - 0.2, 0)) + V(0, 0, zc),
                                    sl_rot.multiply(App.Rotation(V(1, 0, 0), -90)))
    o = feat(doc, part, "CAM_Servo", "Серво_камеры_SG90", sg90(), SERVO)
    o.Placement = App.Placement(A + sv_pl.Base, sv_pl.Rotation)
    for j, ys in enumerate(SG_HOLES_Y):
        sc = cyl(1.0, -6.0, 0.0).fuse(cyl(2.0, 0.0, 1.4))
        pt = sv_pl.Rotation.multVec(V(0, ys, 0)) + sv_pl.Base
        o = feat(doc, part, "CAM_SvScr%d" % (j + 1), "Саморез_SG90_2x6_камера_%d" % (j + 1), sc, DARK)
        o.Placement.Base = V(A.x + pt.x, A.y + pt.y, tab0 + 2.5)
    # шестерня z13 на шлице: зуб 0 смотрит на ступицу при CamAngle = CamStow,
    # дальше крутится выражением (i = 30/13, навстречу ступице)
    gsv = involute_gear(GEAR_M, CAM_GEAR_SV, GEAR_W, bore=4.9, shift=RTP_SHIFT, z0=Hb,
                        phase=math.degrees(phi) + 180.0)
    o = feat(doc, part, "CAM_GearSv", "Шестерня_SG90_камеры_m1_z%d" % CAM_GEAR_SV, gsv, (0.95, 0.95, 0.95))
    o.Placement = App.Placement(A + C, App.Rotation(V(0, 0, 1), 0.001))
    o.setExpression("Placement.Rotation.Angle",
                    "-(%s.CamAngle - %.4f deg) * %d / %d" % (VE, stow, CAM_GEAR_HUB, CAM_GEAR_SV))

    # --- ось: M5 сверху, стопка внутр. колец на буртике головы ---
    zb1, zb2 = Hb, Hb + 13.0                              # низ подшипников
    for k, z0 in enumerate((zb1, zb2)):
        sh = tube(B5["D"] / 2.0, B5["d"] / 2.0, z0, z0 + B5["B"], A.x, A.y)
        feat(doc, part, "CAM_Brg%d" % (k + 1), "Подшипник_консоли_625ZZ_%d" % (k + 1), sh, STEEL)
    feat(doc, part, "CAM_SpIn", "Втулка_оси_камеры_Ø7/Ø5.2x8",
         tube(3.5, 2.6, zb1 + B5["B"], zb2, A.x, A.y), STEEL)
    zh = zb2 + B5["B"] + 1.0
    feat(doc, part, "CAM_SpTop", "Шайба_оси_камеры_Ø7/Ø5.2x1",
         tube(3.5, 2.6, zb2 + B5["B"], zh, A.x, A.y), STEEL)
    Lax = 30
    o = feat(doc, part, "CAM_AxBolt", "Винт_оси_камеры_M5x%d_ISO4762" % Lax, cap_screw(M5, Lax), DARK)
    o.Placement.Base = V(A.x, A.y, zh)
    o = feat(doc, part, "CAM_AxNut", "Гайка_оси_камеры_M5", nut(M5, rot5), STEEL)
    o.Placement.Base = V(A.x, A.y, zn + 0.2)
    if zh - Lax > zn:
        raise RuntimeError("ось камеры: винт M5x%d не доходит до гайки" % Lax)
    if zb - BOOM_D / 2.0 - (zh + M5["k"]) < 0.5:
        raise RuntimeError("консоль ложится на головку оси M5")

    # --- поворотная часть (своя СК: начало — ось консоли, консоль вдоль +X) ---
    boom_p.Placement = App.Placement(V(A.x, A.y, 0), App.Rotation(V(0, 0, 1), e.CamAngle.Value or 0.001))
    boom_p.setExpression("Placement.Rotation.Angle", "%s.CamAngle" % VE)
    # ступица: снизу гнездо 625 №1 и венец z30, сверху — седло хомута консоли.
    # Гнездо 625 №2 открыто вверх, в жёлоб седла: через него ставят
    # подшипник, шайбу и винт оси и затягивают его ключом 4 — до того, как
    # в седло ляжет консоль. Консоль проходит над головкой винта
    hl, hw = HUB_HL, HUB_HW
    blk0 = Hb + GEAR_W + 0.5                              # над шестернёй SG90
    hub = cyl(11.0, Hb, blk0).fuse(box(-hl, hl, -hw, hw, blk0, zb))
    hub = hub.fuse(involute_gear(GEAR_M, CAM_GEAR_HUB, GEAR_W, shift=-RTP_SHIFT, z0=Hb,
                                 phase=math.degrees(phi) - stow + 180.0 / CAM_GEAR_HUB))
    hcut = [cyl(B5["D"] / 2.0, Hb - 1, Hb + B5["B"]),
            cyl(4.25, Hb, zb2),
            cyl(B5["D"] / 2.0, zb2, zb + 1),
            cyl_x(BOOM_D / 2.0, -hl - 1, hl + 1, 0, zb)]
    z_hn = zb - 7.0                                       # гнёзда гаек хомута
    hub_sc = [(xs, s_ * HUB_SY) for xs in (-HUB_SX, HUB_SX) for s_ in (1, -1)]
    for xs, ys in hub_sc:
        hcut.append(cyl(M3["hole"] / 2.0, z_hn - 2.0, zb + 1, xs, ys))
        hcut.append(nut_pocket(M3, z_hn, xs, ys, V(0, 1 if ys > 0 else -1, 0), rot=0.0, depth=12))
    hub = hub.cut(hcut).removeSplitter()
    feat(doc, boom_p, "CAM_Hub", "Ступица_консоли_печать", hub, PLA2)
    capz0, capz1 = zb + HUB_GAP, zb + HUB_CAP
    hcap = box(-hl, hl, -hw, hw, capz0, capz1).cut(cyl_x(BOOM_D / 2.0, -hl - 1, hl + 1, 0, zb))
    for xs, ys in hub_sc:
        hcap = hcap.cut(cyl(M3["hole"] / 2.0, capz0 - 1, capz1 + 1, xs, ys))
        hcap = hcap.cut(cyl(M3["dk"] / 2.0 + 0.25, capz1 - 3.0, capz1 + 1, xs, ys))
    feat(doc, boom_p, "CAM_HubCap", "Ступица_консоли_крышка", hcap.removeSplitter(), PLA2)
    for k, (xs, ys) in enumerate(hub_sc):
        o = feat(doc, boom_p, "CAM_HubScr%d" % (k + 1), "Винт_хомута_консоли_M3x12_%d" % (k + 1),
                 cap_screw(M3, 12), DARK)
        o.Placement.Base = V(xs, ys, capz1 - 3.0)
        o = feat(doc, boom_p, "CAM_HubNut%d" % (k + 1), "Гайка_хомута_консоли_M3_%d" % (k + 1),
                 nut(M3, 0.0), STEEL)
        o.Placement.Base = V(xs, ys, z_hn + 0.2)

    def ycross(x, zc, half):
        """Поперечная стяжка по Y: отверстие + гнездо гайки в лыске -Y."""
        h = Part.makeCylinder(M3["hole"] / 2.0, 2 * half + 2, V(x, -half - 1, zc), V(0, 1, 0))
        hx = hexagon(M3["nut_s"] + 0.3, 0, M3["nut_m"] + 0.2)
        hx.rotate(V(0, 0, 0), V(1, 0, 0), -90)
        hx.translate(V(x, -half - 0.01, zc))
        return [h, hx]
    # консоль: передний конец — в кронштейне камеры (сверловка под стяжку),
    # задний проходит хомут ступицы насквозь; длина — до 10 мм вверх
    L_b = math.ceil((reach + 12.0 + hl) / 10.0) * 10.0
    x_b0 = reach + 12.0 - L_b
    bt = cyl_x(BOOM_D / 2.0, x_b0, reach + 12.0, 0, zb).cut(
        cyl_x(BOOM_D / 2.0 - BOOM_T, x_b0 - 1, reach + 13, 0, zb))
    bt = bt.cut(Part.makeCylinder(M3["hole"] / 2.0, BOOM_D + 2, V(reach - 18.0, -BOOM_D / 2.0 - 1, zb),
                                  V(0, 1, 0)))           # сверловка Ø3.4 под стяжку кронштейна
    feat(doc, boom_p, "CAM_Boom", "Консоль_Al_труба_Ø%gx%g_L%.0f" % (BOOM_D, BOOM_T, L_b), bt, STEEL)

    def yhw(tag, x, half, label):
        rot = App.Rotation(V(1, 0, 0), -90)
        o = feat(doc, boom_p, "CAM_%sScr" % tag, "Винт_%s_M3x18" % label, cap_screw(M3, 18), DARK)
        o.Placement = App.Placement(V(x, half, zb), rot)
        o = feat(doc, boom_p, "CAM_%sNut" % tag, "Гайка_%s_M3" % label, nut(M3, 0.0), STEEL)
        o.Placement = App.Placement(V(x, -half + 0.1, zb), rot)

    # --- кронштейн камеры на конце консоли ---
    R = reach
    rot_c = 90.0 - work            # в работе длинная сторона кадра — вдоль Y полигона
    br = box(R - 26.0, R + 14.0, -9.0, 9.0, zb - 9.0, zb + 9.0)
    z_pl1 = zb - 9.0
    z_pl0 = z_pl1 - 3.0
    hw_ = CAM_PCB / 2.0 + 3.0
    pl = rounded_rect(-hw_, hw_, -hw_, hw_, z_pl0, z_pl1 + 0.01, 3.0)
    z_pcb1 = z_pl0 - 5.0
    for sx in (-1, 1):
        for sy in (-1, 1):
            pl = pl.fuse(cyl(2.6, z_pcb1, z_pl0 + 0.01, sx * CAM_HOLE / 2.0, sy * CAM_HOLE / 2.0))
    pl = pl.cut([cyl(0.8, z_pcb1 - 1, z_pl1 - 0.8, sx * CAM_HOLE / 2.0, sy * CAM_HOLE / 2.0)
                 for sx in (-1, 1) for sy in (-1, 1)])
    pl.rotate(V(0, 0, 0), V(0, 0, 1), rot_c)
    pl.translate(V(R, 0, 0))
    br = br.fuse(pl).cut([cyl_x(BOOM_D / 2.0 + 0.1, R - 27.0, R + 12.0, 0, zb)] +
                         ycross(R - 18.0, zb, 9.0)).removeSplitter()
    feat(doc, boom_p, "CAM_Bracket", "Кронштейн_камеры_печать", br, PLA2)
    yhw("Br", R - 18.0, 9.0, "кронштейна_камеры")
    # плата камеры 38x38 + объектив (держатель 15x15x5, ствол Ø14x10)
    pcb = box(-CAM_PCB / 2.0, CAM_PCB / 2.0, -CAM_PCB / 2.0, CAM_PCB / 2.0, z_pcb1 - 1.6, z_pcb1)
    pcb = pcb.cut([cyl(1.1, z_pcb1 - 3, z_pcb1 + 1, sx * CAM_HOLE / 2.0, sy * CAM_HOLE / 2.0)
                   for sx in (-1, 1) for sy in (-1, 1)])
    pcb = pcb.fuse(box(-6.0, 6.0, CAM_PCB / 2.0 - 8.0, CAM_PCB / 2.0 - 1.0, z_pcb1, z_pcb1 + 3.5))  # разъём USB
    pcb.rotate(V(0, 0, 0), V(0, 0, 1), rot_c)
    pcb.translate(V(R, 0, 0))
    feat(doc, boom_p, "CAM_Board", "Камера_USB_IMX179_плата_38x38", pcb, (0.10, 0.45, 0.20))
    z_l1 = z_pcb1 - 1.6
    lens = box(R - 7.5, R + 7.5, -7.5, 7.5, z_l1 - 5.0, z_l1).fuse(cyl(7.0, z_l1 - 15.0, z_l1 - 5.0, R, 0))
    feat(doc, boom_p, "CAM_Lens", "Камера_объектив", lens, (0.08, 0.08, 0.08))
    for k, (sx, sy) in enumerate(((-1, -1), (-1, 1), (1, -1), (1, 1))):
        q = V(sx * CAM_HOLE / 2.0, sy * CAM_HOLE / 2.0, 0)
        q = App.Rotation(V(0, 0, 1), rot_c).multVec(q)
        sc = cyl(0.95, -8.0, 0.0).fuse(cyl(1.9, 0.0, 1.3))     # саморез M2x8, снизу сквозь плату
        o = feat(doc, boom_p, "CAM_BoardScr%d" % (k + 1), "Саморез_M2x8_камеры_%d" % (k + 1), sc, DARK)
        o.Placement = App.Placement(V(R + q.x, q.y, z_l1), App.Rotation(V(1, 0, 0), 180))
    doc.recompute()
    h_lens = z_l1 - 15.0 - fl
    if abs(h_lens - e.CamLensH.Value) > 1e-6:
        raise RuntimeError("объектив на %.2f, а не на CamLensH" % h_lens)
    return dict(reach=reach, work=work, stow=stow, h=h_lens, L_b=L_b, tail=-x_b0 - hl,
                mast_up=z_mt - z_s1, off=math.degrees(psi),
                servo=(stow - work) * CAM_GEAR_HUB / CAM_GEAR_SV)


def poly_to_robot(d, e, px, py):
    return V(px - e.PolyShaftX.Value + d.PulleyAxisX.Value,
             py - e.PolyShaftY.Value + d.ArmAxisY.Value, e.FloorZ.Value)


def cell_centers():
    """Центры клеток и отбоя в координатах полигона: (имя, x, y)."""
    O_GX, O_GY = 370.0 + 193.0, (85.0 + (330.0 + 297.0) / 2.0) - 272.0   # метка id 27
    out = []
    for k, row in enumerate("АБВГДЕ"):
        for n in range(9):
            out.append(("%s%d" % (row, n), O_GX - 28.0 * (k + 1), O_GY + 28.0 * n))
    for k in range(1, 6):
        out.append(("Отбой%d" % k, O_GX - 28.0 * k, O_GY + 252.0))
    return out


def build_polygon(doc, d, e):
    purge(doc, ("PG_",))
    g = doc.getObject(POLY_GROUP)
    if g is None:
        g = doc.addObject("App::DocumentObjectGroup", POLY_GROUP)
    g.Label = "Полигон_ЕТЗ_ссылка"
    o0 = poly_to_robot(d, e, 0, 0)
    zones = [("PG_Zone1", "Зона_1_350x500", (0, 350, 0, 500), (0.92, 0.92, 0.92)),
             ("PG_Zone2a", "Зона_2_низ", (350, 600, 0, 80), (0.80, 0.80, 0.80)),
             ("PG_Zone2b", "Зона_2_верх", (350, 600, 420, 500), (0.80, 0.80, 0.80)),
             ("PG_Field", "Область_поля_250x330", (350, 600, 85, 415), (0.62, 0.62, 0.62))]
    for name, label, (x0, x1, y0, y1), col in zones:
        s = box(o0.x + x0, o0.x + x1, o0.y + y0, o0.y + y1, o0.z - 0.4, o0.z - 0.2)
        o = doc.addObject("Part::Feature", name)
        o.Shape = s
        o.Label = label
        g.addObject(o)
        if App.GuiUp:
            o.ViewObject.ShapeColor = col
    sheet = box(o0.x + 370, o0.x + 580, o0.y + 101.5, o0.y + 398.5, o0.z - 0.2, o0.z - 0.1)
    o = doc.addObject("Part::Feature", "PG_Sheet")
    o.Shape = sheet
    o.Label = "Лист_А4_поля"
    g.addObject(o)
    marks = []
    for nm, px, py in cell_centers():
        p = poly_to_robot(d, e, px, py)
        marks.append(Part.makeCylinder(3.0, 0.1, V(p.x, p.y, p.z - 0.1)))
    o = doc.addObject("Part::Feature", "PG_Cells")
    o.Shape = Part.makeCompound(marks)
    o.Label = "Центры_клеток_и_отбоя"
    g.addObject(o)
    if App.GuiUp:
        o.ViewObject.ShapeColor = (0.0, 0.0, 0.0)
    doc.recompute()
    return g


def main():
    doc = pick_doc()
    d = doc.getObject(VS)
    if doc.getObject("Poza") is None:
        # старый документ: углы руки ещё в Drive — перенести в VarSet Poza
        import os
        path = os.path.join(os.path.dirname(doc.FileName), "shkiv_param.FCMacro")
        ns = {"__name__": "shkiv_lib"}
        exec(compile(open(path, encoding="utf-8").read(), path, "exec"), ns)
        ns["upgrade_pose"](doc)
    e = ensure_vs(doc)
    doc.recompute()
    build_frame(doc, d, e)
    eff, carr, info = build_effector(doc, d, e)
    cam = build_camera(doc, d, e)
    build_polygon(doc, d, e)
    doc.recompute()
    print("станина, ремни, рабочий узел, камера, полигон — построены")
    print("  камера: консоль %.1f мм, в работе %.1f°, сложена %.1f° (SG90 %.0f°), объектив %.0f мм над полем"
          % (cam["reach"], cam["work"], cam["stow"], cam["servo"], cam["h"]))
    print("  ось консоли вынесена от мачты на %.0f мм (под %.1f°); мачта над головой %.1f мм; "
          "консоль L%.0f, за хомутом ступицы %.1f мм"
          % (CAM_OFF, cam["off"], cam["mast_up"], cam["L_b"], cam["tail"]))
    print("  ход Z %.1f мм за 180° SG90 (шестерня m1 z%d), губа присоски от поля +4 до +%.1f"
          % (Z_STROKE, ZP_TEETH, 4.0 + Z_STROKE))
    print("  поворот: z%d -> z%d, i = %.1f: 180° серво = %.0f° захвата"
          % (RTP_TEETH, SPG_TEETH, SPG_TEETH / float(RTP_TEETH), 180.0 * SPG_TEETH / RTP_TEETH))
    print("  вылет захвата от оси локтя %.1f мм; захват — присоска DP8 на оси шпинделя, винт шпинделя %s"
          % (SPINDLE_X, doc.getObject("CR_Screw").Label))
    bad = [(o.Name, o.State) for o in doc.Objects if "Invalid" in o.State]
    if bad:
        print("  !! невалидные объекты:", bad)


if __name__ == "__main__":
    main()
